package port_definition {
    private import general_definition::*;
    port def PT_PT_MEA_004 {
    out item payload : I_ITM_MEA_004;
    }
    port def PT_PT_MEA_005 {
    out item payload : I_ITM_MEA_005;
    }
    port def PT_PT_MEA_006 {
    out item payload : I_ITM_MEA_006;
    }
    port def PT_PT_MEA_011 {
    out item payload : I_ITM_MEA_011;
    }
    port def PT_PT_MEA_012 {
    out item payload : I_ITM_MEA_012;
    }
    port def PT_PT_PHY_001 {
    inout item payload : I_ITM_PHY_001;
    }
    port def PT_PT_PHY_004 {
    inout item payload : I_ITM_PHY_004;
    }
    port def PT_PT_PHY_005 {
    inout item payload : I_ITM_PHY_005;
    }
    port def PT_PT_PHY_007 {
    inout item payload : I_ITM_PHY_007;
    }
    port def PT_PT_PHY_014 {
    inout item payload : I_ITM_PHY_014;
    }
    port def PT_PT_STA_013 {
    out item payload : I_ITM_STA_013;
    }
    port def PT_PT_STA_016 {
    out item payload : I_ITM_STA_016;
    }
}
