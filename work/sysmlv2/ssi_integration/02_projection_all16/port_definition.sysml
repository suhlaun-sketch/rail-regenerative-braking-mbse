package port_definition {
    private import general_definition::*;
    port def PT_PT_ACC_002 {
    out item payload : I_ITM_ACC_002;
    }
    port def PT_PT_ACC_003 {
    out item payload : I_ITM_ACC_003;
    }
    port def PT_PT_ACC_004 {
    out item payload : I_ITM_ACC_004;
    }
    port def PT_PT_ACC_005 {
    out item payload : I_ITM_ACC_005;
    }
    port def PT_PT_CMD_001 {
    out item payload : I_ITM_CMD_001;
    }
    port def PT_PT_CMD_002 {
    out item payload : I_ITM_CMD_002;
    }
    port def PT_PT_CMD_003 {
    out item payload : I_ITM_CMD_003;
    }
    port def PT_PT_CMD_004 {
    out item payload : I_ITM_CMD_004;
    }
    port def PT_PT_CMD_006 {
    out item payload : I_ITM_CMD_006;
    }
    port def PT_PT_CMD_012 {
    out item payload : I_ITM_CMD_012;
    }
    port def PT_PT_CMD_016 {
    out item payload : I_ITM_CMD_016;
    }
    port def PT_PT_CMD_018 {
    out item payload : I_ITM_CMD_018;
    }
    port def PT_PT_CMD_024 {
    out item payload : I_ITM_CMD_024;
    }
    port def PT_PT_CMD_025 {
    out item payload : I_ITM_CMD_025;
    }
    port def PT_PT_CMD_026 {
    out item payload : I_ITM_CMD_026;
    }
    port def PT_PT_CMD_027 {
    out item payload : I_ITM_CMD_027;
    }
    port def PT_PT_CMD_028 {
    out item payload : I_ITM_CMD_028;
    }
    port def PT_PT_CMD_029 {
    out item payload : I_ITM_CMD_029;
    }
    port def PT_PT_CMD_030 {
    out item payload : I_ITM_CMD_030;
    }
    port def PT_PT_LIM_001 {
    out item payload : I_ITM_LIM_001;
    }
    port def PT_PT_LIM_005 {
    out item payload : I_ITM_LIM_005;
    }
    port def PT_PT_LIM_009 {
    out item payload : I_ITM_LIM_009;
    }
    port def PT_PT_LIM_010 {
    out item payload : I_ITM_LIM_010;
    }
    port def PT_PT_MEA_004 {
    out item payload : I_ITM_MEA_004;
    }
    port def PT_PT_MEA_005 {
    out item payload : I_ITM_MEA_005;
    }
    port def PT_PT_MEA_006 {
    out item payload : I_ITM_MEA_006;
    }
    port def PT_PT_MEA_008 {
    out item payload : I_ITM_MEA_008;
    }
    port def PT_PT_MEA_009 {
    out item payload : I_ITM_MEA_009;
    }
    port def PT_PT_MEA_011 {
    out item payload : I_ITM_MEA_011;
    }
    port def PT_PT_MEA_012 {
    out item payload : I_ITM_MEA_012;
    }
    port def PT_PT_MEA_013 {
    out item payload : I_ITM_MEA_013;
    }
    port def PT_PT_MEA_014 {
    out item payload : I_ITM_MEA_014;
    }
    port def PT_PT_MEA_016 {
    out item payload : I_ITM_MEA_016;
    }
    port def PT_PT_MEA_028 {
    out item payload : I_ITM_MEA_028;
    }
    port def PT_PT_MEA_029 {
    out item payload : I_ITM_MEA_029;
    }
    port def PT_PT_PHY_001 {
    inout item payload : I_ITM_PHY_001;
    }
    port def PT_PT_PHY_004 {
    inout item payload : I_ITM_PHY_004;
    }
    port def PT_PT_PHY_005 {
    inout item payload : I_ITM_PHY_005;
    }
    port def PT_PT_PHY_007 {
    inout item payload : I_ITM_PHY_007;
    }
    port def PT_PT_PHY_014 {
    inout item payload : I_ITM_PHY_014;
    }
    port def PT_PT_STA_002 {
    out item payload : I_ITM_STA_002;
    }
    port def PT_PT_STA_003 {
    out item payload : I_ITM_STA_003;
    }
    port def PT_PT_STA_013 {
    out item payload : I_ITM_STA_013;
    }
    port def PT_PT_STA_015 {
    out item payload : I_ITM_STA_015;
    }
    port def PT_PT_STA_016 {
    out item payload : I_ITM_STA_016;
    }
    port def PT_PT_STA_019 {
    out item payload : I_ITM_STA_019;
    }
    port def PT_PT_STA_024 {
    out item payload : I_ITM_STA_024;
    }
    port def PT_PT_STA_025 {
    out item payload : I_ITM_STA_025;
    }
    port def PT_PT_STA_027 {
    out item payload : I_ITM_STA_027;
    }
    port def PT_PT_STA_030 {
    out item payload : I_ITM_STA_030;
    }
    port def PT_PT_STA_031 {
    out item payload : I_ITM_STA_031;
    }
}
