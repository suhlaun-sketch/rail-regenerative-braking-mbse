package general_definition {
    part def P_N_3100;
    part def P_N_3500;
    part def P_N_3600;
    part def P_N_3800;
    part def P_N_4100;
    part def P_N_4200;
    part def P_N_4400;
    part def P_N_4500;
    part def P_N_5100;
    part def P_N_5300;
    part def P_N_7100;
    part def P_N_7200;
    part def P_N_8100;
    part def P_D100;
    part def P_E100;
    part def P_X100;
    item def I_ITM_ACC_002;
    item def I_ITM_ACC_003;
    item def I_ITM_ACC_004;
    item def I_ITM_ACC_005;
    item def I_ITM_CMD_001;
    item def I_ITM_CMD_002;
    item def I_ITM_CMD_003;
    item def I_ITM_CMD_004;
    item def I_ITM_CMD_006;
    item def I_ITM_CMD_012;
    item def I_ITM_CMD_016;
    item def I_ITM_CMD_018;
    item def I_ITM_CMD_024;
    item def I_ITM_CMD_025;
    item def I_ITM_CMD_026;
    item def I_ITM_CMD_027;
    item def I_ITM_CMD_028;
    item def I_ITM_CMD_029;
    item def I_ITM_CMD_030;
    item def I_ITM_LIM_001;
    item def I_ITM_LIM_005;
    item def I_ITM_LIM_009;
    item def I_ITM_LIM_010;
    item def I_ITM_MEA_004;
    item def I_ITM_MEA_005;
    item def I_ITM_MEA_006;
    item def I_ITM_MEA_008;
    item def I_ITM_MEA_009;
    item def I_ITM_MEA_011;
    item def I_ITM_MEA_012;
    item def I_ITM_MEA_013;
    item def I_ITM_MEA_014;
    item def I_ITM_MEA_016;
    item def I_ITM_MEA_028;
    item def I_ITM_MEA_029;
    item def I_ITM_PHY_001;
    item def I_ITM_PHY_004;
    item def I_ITM_PHY_005;
    item def I_ITM_PHY_007;
    item def I_ITM_PHY_014;
    item def I_ITM_STA_002;
    item def I_ITM_STA_003;
    item def I_ITM_STA_013;
    item def I_ITM_STA_015;
    item def I_ITM_STA_016;
    item def I_ITM_STA_019;
    item def I_ITM_STA_024;
    item def I_ITM_STA_025;
    item def I_ITM_STA_027;
    item def I_ITM_STA_030;
    item def I_ITM_STA_031;
}
