package interface_definition {
    private import general_definition::*;
    private import port_definition::*;
    interface def IF_IF_ACC_002 {
    end source : PT_PT_ACC_002;
    end target : ~PT_PT_ACC_002;
    flow of I_ITM_ACC_002 from source.payload to target.payload;
    }
    interface def IF_IF_ACC_003 {
    end source : PT_PT_ACC_003;
    end target : ~PT_PT_ACC_003;
    flow of I_ITM_ACC_003 from source.payload to target.payload;
    }
    interface def IF_IF_ACC_004 {
    end source : PT_PT_ACC_004;
    end target : ~PT_PT_ACC_004;
    flow of I_ITM_ACC_004 from source.payload to target.payload;
    }
    interface def IF_IF_ACC_005 {
    end source : PT_PT_ACC_005;
    end target : ~PT_PT_ACC_005;
    flow of I_ITM_ACC_005 from source.payload to target.payload;
    }
    interface def IF_IF_CMD_001 {
    end source : PT_PT_CMD_001;
    end target : ~PT_PT_CMD_001;
    flow of I_ITM_CMD_001 from source.payload to target.payload;
    }
    interface def IF_IF_CMD_002 {
    end source : PT_PT_CMD_002;
    end target : ~PT_PT_CMD_002;
    flow of I_ITM_CMD_002 from source.payload to target.payload;
    }
    interface def IF_IF_CMD_003 {
    end source : PT_PT_CMD_003;
    end target : ~PT_PT_CMD_003;
    flow of I_ITM_CMD_003 from source.payload to target.payload;
    }
    interface def IF_IF_CMD_004 {
    end source : PT_PT_CMD_004;
    end target : ~PT_PT_CMD_004;
    flow of I_ITM_CMD_004 from source.payload to target.payload;
    }
    interface def IF_IF_CMD_006 {
    end source : PT_PT_CMD_006;
    end target : ~PT_PT_CMD_006;
    flow of I_ITM_CMD_006 from source.payload to target.payload;
    }
    interface def IF_IF_CMD_012 {
    end source : PT_PT_CMD_012;
    end target : ~PT_PT_CMD_012;
    flow of I_ITM_CMD_012 from source.payload to target.payload;
    }
    interface def IF_IF_CMD_016 {
    end source : PT_PT_CMD_016;
    end target : ~PT_PT_CMD_016;
    flow of I_ITM_CMD_016 from source.payload to target.payload;
    }
    interface def IF_IF_CMD_018 {
    end source : PT_PT_CMD_018;
    end target : ~PT_PT_CMD_018;
    flow of I_ITM_CMD_018 from source.payload to target.payload;
    }
    interface def IF_IF_CMD_024 {
    end source : PT_PT_CMD_024;
    end target : ~PT_PT_CMD_024;
    flow of I_ITM_CMD_024 from source.payload to target.payload;
    }
    interface def IF_IF_CMD_025 {
    end source : PT_PT_CMD_025;
    end target : ~PT_PT_CMD_025;
    flow of I_ITM_CMD_025 from source.payload to target.payload;
    }
    interface def IF_IF_CMD_026 {
    end source : PT_PT_CMD_026;
    end target : ~PT_PT_CMD_026;
    flow of I_ITM_CMD_026 from source.payload to target.payload;
    }
    interface def IF_IF_CMD_027 {
    end source : PT_PT_CMD_027;
    end target : ~PT_PT_CMD_027;
    flow of I_ITM_CMD_027 from source.payload to target.payload;
    }
    interface def IF_IF_CMD_028 {
    end source : PT_PT_CMD_028;
    end target : ~PT_PT_CMD_028;
    flow of I_ITM_CMD_028 from source.payload to target.payload;
    }
    interface def IF_IF_CMD_029 {
    end source : PT_PT_CMD_029;
    end target : ~PT_PT_CMD_029;
    flow of I_ITM_CMD_029 from source.payload to target.payload;
    }
    interface def IF_IF_CMD_030 {
    end source : PT_PT_CMD_030;
    end target : ~PT_PT_CMD_030;
    flow of I_ITM_CMD_030 from source.payload to target.payload;
    }
    interface def IF_IF_LIM_001 {
    end source : PT_PT_LIM_001;
    end target : ~PT_PT_LIM_001;
    flow of I_ITM_LIM_001 from source.payload to target.payload;
    }
    interface def IF_IF_LIM_005 {
    end source : PT_PT_LIM_005;
    end target : ~PT_PT_LIM_005;
    flow of I_ITM_LIM_005 from source.payload to target.payload;
    }
    interface def IF_IF_LIM_009 {
    end source : PT_PT_LIM_009;
    end target : ~PT_PT_LIM_009;
    flow of I_ITM_LIM_009 from source.payload to target.payload;
    }
    interface def IF_IF_LIM_010 {
    end source : PT_PT_LIM_010;
    end target : ~PT_PT_LIM_010;
    flow of I_ITM_LIM_010 from source.payload to target.payload;
    }
    interface def IF_IF_MEA_004 {
    end source : PT_PT_MEA_004;
    end target : ~PT_PT_MEA_004;
    flow of I_ITM_MEA_004 from source.payload to target.payload;
    }
    interface def IF_IF_MEA_005 {
    end source : PT_PT_MEA_005;
    end target : ~PT_PT_MEA_005;
    flow of I_ITM_MEA_005 from source.payload to target.payload;
    }
    interface def IF_IF_MEA_006 {
    end source : PT_PT_MEA_006;
    end target : ~PT_PT_MEA_006;
    flow of I_ITM_MEA_006 from source.payload to target.payload;
    }
    interface def IF_IF_MEA_008 {
    end source : PT_PT_MEA_008;
    end target : ~PT_PT_MEA_008;
    flow of I_ITM_MEA_008 from source.payload to target.payload;
    }
    interface def IF_IF_MEA_009 {
    end source : PT_PT_MEA_009;
    end target : ~PT_PT_MEA_009;
    flow of I_ITM_MEA_009 from source.payload to target.payload;
    }
    interface def IF_IF_MEA_011 {
    end source : PT_PT_MEA_011;
    end target : ~PT_PT_MEA_011;
    flow of I_ITM_MEA_011 from source.payload to target.payload;
    }
    interface def IF_IF_MEA_012 {
    end source : PT_PT_MEA_012;
    end target : ~PT_PT_MEA_012;
    flow of I_ITM_MEA_012 from source.payload to target.payload;
    }
    interface def IF_IF_MEA_013 {
    end source : PT_PT_MEA_013;
    end target : ~PT_PT_MEA_013;
    flow of I_ITM_MEA_013 from source.payload to target.payload;
    }
    interface def IF_IF_MEA_014 {
    end source : PT_PT_MEA_014;
    end target : ~PT_PT_MEA_014;
    flow of I_ITM_MEA_014 from source.payload to target.payload;
    }
    interface def IF_IF_MEA_016 {
    end source : PT_PT_MEA_016;
    end target : ~PT_PT_MEA_016;
    flow of I_ITM_MEA_016 from source.payload to target.payload;
    }
    interface def IF_IF_MEA_028 {
    end source : PT_PT_MEA_028;
    end target : ~PT_PT_MEA_028;
    flow of I_ITM_MEA_028 from source.payload to target.payload;
    }
    interface def IF_IF_MEA_029 {
    end source : PT_PT_MEA_029;
    end target : ~PT_PT_MEA_029;
    flow of I_ITM_MEA_029 from source.payload to target.payload;
    }
    interface def IF_IF_PHY_001 {
    end source : PT_PT_PHY_001;
    end target : PT_PT_PHY_001;
    flow of I_ITM_PHY_001 from source.payload to target.payload;
    }
    interface def IF_IF_PHY_004 {
    end source : PT_PT_PHY_004;
    end target : PT_PT_PHY_004;
    flow of I_ITM_PHY_004 from source.payload to target.payload;
    }
    interface def IF_IF_PHY_005 {
    end source : PT_PT_PHY_005;
    end target : PT_PT_PHY_005;
    flow of I_ITM_PHY_005 from source.payload to target.payload;
    }
    interface def IF_IF_PHY_007 {
    end source : PT_PT_PHY_007;
    end target : PT_PT_PHY_007;
    flow of I_ITM_PHY_007 from source.payload to target.payload;
    }
    interface def IF_IF_PHY_014 {
    end source : PT_PT_PHY_014;
    end target : PT_PT_PHY_014;
    flow of I_ITM_PHY_014 from source.payload to target.payload;
    }
    interface def IF_IF_STA_002 {
    end source : PT_PT_STA_002;
    end target : ~PT_PT_STA_002;
    flow of I_ITM_STA_002 from source.payload to target.payload;
    }
    interface def IF_IF_STA_003 {
    end source : PT_PT_STA_003;
    end target : ~PT_PT_STA_003;
    flow of I_ITM_STA_003 from source.payload to target.payload;
    }
    interface def IF_IF_STA_013 {
    end source : PT_PT_STA_013;
    end target : ~PT_PT_STA_013;
    flow of I_ITM_STA_013 from source.payload to target.payload;
    }
    interface def IF_IF_STA_015 {
    end source : PT_PT_STA_015;
    end target : ~PT_PT_STA_015;
    flow of I_ITM_STA_015 from source.payload to target.payload;
    }
    interface def IF_IF_STA_016 {
    end source : PT_PT_STA_016;
    end target : ~PT_PT_STA_016;
    flow of I_ITM_STA_016 from source.payload to target.payload;
    }
    interface def IF_IF_STA_019 {
    end source : PT_PT_STA_019;
    end target : ~PT_PT_STA_019;
    flow of I_ITM_STA_019 from source.payload to target.payload;
    }
    interface def IF_IF_STA_024 {
    end source : PT_PT_STA_024;
    end target : ~PT_PT_STA_024;
    flow of I_ITM_STA_024 from source.payload to target.payload;
    }
    interface def IF_IF_STA_025 {
    end source : PT_PT_STA_025;
    end target : ~PT_PT_STA_025;
    flow of I_ITM_STA_025 from source.payload to target.payload;
    }
    interface def IF_IF_STA_027 {
    end source : PT_PT_STA_027;
    end target : ~PT_PT_STA_027;
    flow of I_ITM_STA_027 from source.payload to target.payload;
    }
    interface def IF_IF_STA_030 {
    end source : PT_PT_STA_030;
    end target : ~PT_PT_STA_030;
    flow of I_ITM_STA_030 from source.payload to target.payload;
    }
    interface def IF_IF_STA_031 {
    end source : PT_PT_STA_031;
    end target : ~PT_PT_STA_031;
    flow of I_ITM_STA_031 from source.payload to target.payload;
    }
}
