package InterfaceDefinitions {
    private import ItemDefinitions::*;
    private import PortDefinitions::*;
    interface def IF_IF_ACC_001 {
        end source : PT_PT_ACC_001;
        end target : ~PT_PT_ACC_001;
        flow of I_ITM_ACC_001 from source.payload to target.payload;
    }
    interface def IF_IF_ACC_002 {
        end source : PT_PT_ACC_002;
        end target : ~PT_PT_ACC_002;
        flow of I_ITM_ACC_002 from source.payload to target.payload;
    }
    interface def IF_IF_ACC_003 {
        end source : PT_PT_ACC_003;
        end target : ~PT_PT_ACC_003;
        flow of I_ITM_ACC_003 from source.payload to target.payload;
    }
    interface def IF_IF_ACC_004 {
        end source : PT_PT_ACC_004;
        end target : ~PT_PT_ACC_004;
        flow of I_ITM_ACC_004 from source.payload to target.payload;
    }
    interface def IF_IF_ACC_005 {
        end source : PT_PT_ACC_005;
        end target : ~PT_PT_ACC_005;
        flow of I_ITM_ACC_005 from source.payload to target.payload;
    }
    interface def IF_IF_ACC_006 {
        end source : PT_PT_ACC_006;
        end target : ~PT_PT_ACC_006;
        flow of I_ITM_ACC_006 from source.payload to target.payload;
    }
    interface def IF_IF_ACC_007 {
        end source : PT_PT_ACC_007;
        end target : ~PT_PT_ACC_007;
        flow of I_ITM_ACC_007 from source.payload to target.payload;
    }
    interface def IF_IF_ACC_008 {
        end source : PT_PT_ACC_008;
        end target : ~PT_PT_ACC_008;
        flow of I_ITM_ACC_008 from source.payload to target.payload;
    }
    interface def IF_IF_ACC_009 {
        end source : PT_PT_ACC_009;
        end target : ~PT_PT_ACC_009;
        flow of I_ITM_ACC_009 from source.payload to target.payload;
    }
    interface def IF_IF_ACC_010 {
        end source : PT_PT_ACC_010;
        end target : ~PT_PT_ACC_010;
        flow of I_ITM_ACC_010 from source.payload to target.payload;
    }
    interface def IF_IF_ACC_011 {
        end source : PT_PT_ACC_011;
        end target : ~PT_PT_ACC_011;
        flow of I_ITM_ACC_011 from source.payload to target.payload;
    }
    interface def IF_IF_ACC_012 {
        end source : PT_PT_ACC_012;
        end target : ~PT_PT_ACC_012;
        flow of I_ITM_ACC_012 from source.payload to target.payload;
    }
    interface def IF_IF_ACC_013 {
        end source : PT_PT_ACC_013;
        end target : ~PT_PT_ACC_013;
        flow of I_ITM_ACC_013 from source.payload to target.payload;
    }
    interface def IF_IF_ACC_014 {
        end source : PT_PT_ACC_014;
        end target : ~PT_PT_ACC_014;
        flow of I_ITM_ACC_014 from source.payload to target.payload;
    }
    interface def IF_IF_ACC_015 {
        end source : PT_PT_ACC_015;
        end target : ~PT_PT_ACC_015;
        flow of I_ITM_ACC_015 from source.payload to target.payload;
    }
    interface def IF_IF_CMD_001 {
        end source : PT_PT_CMD_001;
        end target : ~PT_PT_CMD_001;
        flow of I_ITM_CMD_001 from source.payload to target.payload;
    }
    interface def IF_IF_CMD_002 {
        end source : PT_PT_CMD_002;
        end target : ~PT_PT_CMD_002;
        flow of I_ITM_CMD_002 from source.payload to target.payload;
    }
    interface def IF_IF_CMD_003 {
        end source : PT_PT_CMD_003;
        end target : ~PT_PT_CMD_003;
        flow of I_ITM_CMD_003 from source.payload to target.payload;
    }
    interface def IF_IF_CMD_004 {
        end source : PT_PT_CMD_004;
        end target : ~PT_PT_CMD_004;
        flow of I_ITM_CMD_004 from source.payload to target.payload;
    }
    interface def IF_IF_CMD_005 {
        end source : PT_PT_CMD_005;
        end target : ~PT_PT_CMD_005;
        flow of I_ITM_CMD_005 from source.payload to target.payload;
    }
    interface def IF_IF_CMD_006 {
        end source : PT_PT_CMD_006;
        end target : ~PT_PT_CMD_006;
        flow of I_ITM_CMD_006 from source.payload to target.payload;
    }
    interface def IF_IF_CMD_007 {
        end source : PT_PT_CMD_007;
        end target : ~PT_PT_CMD_007;
        flow of I_ITM_CMD_007 from source.payload to target.payload;
    }
    interface def IF_IF_CMD_008 {
        end source : PT_PT_CMD_008;
        end target : ~PT_PT_CMD_008;
        flow of I_ITM_CMD_008 from source.payload to target.payload;
    }
    interface def IF_IF_CMD_009 {
        end source : PT_PT_CMD_009;
        end target : ~PT_PT_CMD_009;
        flow of I_ITM_CMD_009 from source.payload to target.payload;
    }
    interface def IF_IF_CMD_010 {
        end source : PT_PT_CMD_010;
        end target : ~PT_PT_CMD_010;
        flow of I_ITM_CMD_010 from source.payload to target.payload;
    }
    interface def IF_IF_CMD_011 {
        end source : PT_PT_CMD_011;
        end target : ~PT_PT_CMD_011;
        flow of I_ITM_CMD_011 from source.payload to target.payload;
    }
    interface def IF_IF_CMD_012 {
        end source : PT_PT_CMD_012;
        end target : ~PT_PT_CMD_012;
        flow of I_ITM_CMD_012 from source.payload to target.payload;
    }
    interface def IF_IF_CMD_013 {
        end source : PT_PT_CMD_013;
        end target : ~PT_PT_CMD_013;
        flow of I_ITM_CMD_013 from source.payload to target.payload;
    }
    interface def IF_IF_CMD_014 {
        end source : PT_PT_CMD_014;
        end target : ~PT_PT_CMD_014;
        flow of I_ITM_CMD_014 from source.payload to target.payload;
    }
    interface def IF_IF_CMD_015 {
        end source : PT_PT_CMD_015;
        end target : ~PT_PT_CMD_015;
        flow of I_ITM_CMD_015 from source.payload to target.payload;
    }
    interface def IF_IF_CMD_016 {
        end source : PT_PT_CMD_016;
        end target : ~PT_PT_CMD_016;
        flow of I_ITM_CMD_016 from source.payload to target.payload;
    }
    interface def IF_IF_CMD_017 {
        end source : PT_PT_CMD_017;
        end target : ~PT_PT_CMD_017;
        flow of I_ITM_CMD_017 from source.payload to target.payload;
    }
    interface def IF_IF_CMD_018 {
        end source : PT_PT_CMD_018;
        end target : ~PT_PT_CMD_018;
        flow of I_ITM_CMD_018 from source.payload to target.payload;
    }
    interface def IF_IF_CMD_019 {
        end source : PT_PT_CMD_019;
        end target : ~PT_PT_CMD_019;
        flow of I_ITM_CMD_019 from source.payload to target.payload;
    }
    interface def IF_IF_CMD_020 {
        end source : PT_PT_CMD_020;
        end target : ~PT_PT_CMD_020;
        flow of I_ITM_CMD_020 from source.payload to target.payload;
    }
    interface def IF_IF_CMD_021 {
        end source : PT_PT_CMD_021;
        end target : ~PT_PT_CMD_021;
        flow of I_ITM_CMD_021 from source.payload to target.payload;
    }
    interface def IF_IF_CMD_022 {
        end source : PT_PT_CMD_022;
        end target : ~PT_PT_CMD_022;
        flow of I_ITM_CMD_022 from source.payload to target.payload;
    }
    interface def IF_IF_CMD_023 {
        end source : PT_PT_CMD_023;
        end target : ~PT_PT_CMD_023;
        flow of I_ITM_CMD_023 from source.payload to target.payload;
    }
    interface def IF_IF_CMD_024 {
        end source : PT_PT_CMD_024;
        end target : ~PT_PT_CMD_024;
        flow of I_ITM_CMD_024 from source.payload to target.payload;
    }
    interface def IF_IF_CMD_025 {
        end source : PT_PT_CMD_025;
        end target : ~PT_PT_CMD_025;
        flow of I_ITM_CMD_025 from source.payload to target.payload;
    }
    interface def IF_IF_CMD_026 {
        end source : PT_PT_CMD_026;
        end target : ~PT_PT_CMD_026;
        flow of I_ITM_CMD_026 from source.payload to target.payload;
    }
    interface def IF_IF_CMD_027 {
        end source : PT_PT_CMD_027;
        end target : ~PT_PT_CMD_027;
        flow of I_ITM_CMD_027 from source.payload to target.payload;
    }
    interface def IF_IF_CMD_028 {
        end source : PT_PT_CMD_028;
        end target : ~PT_PT_CMD_028;
        flow of I_ITM_CMD_028 from source.payload to target.payload;
    }
    interface def IF_IF_CMD_029 {
        end source : PT_PT_CMD_029;
        end target : ~PT_PT_CMD_029;
        flow of I_ITM_CMD_029 from source.payload to target.payload;
    }
    interface def IF_IF_CMD_030 {
        end source : PT_PT_CMD_030;
        end target : ~PT_PT_CMD_030;
        flow of I_ITM_CMD_030 from source.payload to target.payload;
    }
    interface def IF_IF_CMD_031 {
        end source : PT_PT_CMD_031;
        end target : ~PT_PT_CMD_031;
        flow of I_ITM_CMD_031 from source.payload to target.payload;
    }
    interface def IF_IF_CMD_032 {
        end source : PT_PT_CMD_032;
        end target : ~PT_PT_CMD_032;
        flow of I_ITM_CMD_032 from source.payload to target.payload;
    }
    interface def IF_IF_LIM_001 {
        end source : PT_PT_LIM_001;
        end target : ~PT_PT_LIM_001;
        flow of I_ITM_LIM_001 from source.payload to target.payload;
    }
    interface def IF_IF_LIM_002 {
        end source : PT_PT_LIM_002;
        end target : ~PT_PT_LIM_002;
        flow of I_ITM_LIM_002 from source.payload to target.payload;
    }
    interface def IF_IF_LIM_003 {
        end source : PT_PT_LIM_003;
        end target : ~PT_PT_LIM_003;
        flow of I_ITM_LIM_003 from source.payload to target.payload;
    }
    interface def IF_IF_LIM_004 {
        end source : PT_PT_LIM_004;
        end target : ~PT_PT_LIM_004;
        flow of I_ITM_LIM_004 from source.payload to target.payload;
    }
    interface def IF_IF_LIM_005 {
        end source : PT_PT_LIM_005;
        end target : ~PT_PT_LIM_005;
        flow of I_ITM_LIM_005 from source.payload to target.payload;
    }
    interface def IF_IF_LIM_006 {
        end source : PT_PT_LIM_006;
        end target : ~PT_PT_LIM_006;
        flow of I_ITM_LIM_006 from source.payload to target.payload;
    }
    interface def IF_IF_LIM_007 {
        end source : PT_PT_LIM_007;
        end target : ~PT_PT_LIM_007;
        flow of I_ITM_LIM_007 from source.payload to target.payload;
    }
    interface def IF_IF_LIM_008 {
        end source : PT_PT_LIM_008;
        end target : ~PT_PT_LIM_008;
        flow of I_ITM_LIM_008 from source.payload to target.payload;
    }
    interface def IF_IF_LIM_009 {
        end source : PT_PT_LIM_009;
        end target : ~PT_PT_LIM_009;
        flow of I_ITM_LIM_009 from source.payload to target.payload;
    }
    interface def IF_IF_LIM_010 {
        end source : PT_PT_LIM_010;
        end target : ~PT_PT_LIM_010;
        flow of I_ITM_LIM_010 from source.payload to target.payload;
    }
    interface def IF_IF_LIM_011 {
        end source : PT_PT_LIM_011;
        end target : ~PT_PT_LIM_011;
        flow of I_ITM_LIM_011 from source.payload to target.payload;
    }
    interface def IF_IF_LIM_012 {
        end source : PT_PT_LIM_012;
        end target : ~PT_PT_LIM_012;
        flow of I_ITM_LIM_012 from source.payload to target.payload;
    }
    interface def IF_IF_LIM_013 {
        end source : PT_PT_LIM_013;
        end target : ~PT_PT_LIM_013;
        flow of I_ITM_LIM_013 from source.payload to target.payload;
    }
    interface def IF_IF_LIM_014 {
        end source : PT_PT_LIM_014;
        end target : ~PT_PT_LIM_014;
        flow of I_ITM_LIM_014 from source.payload to target.payload;
    }
    interface def IF_IF_MEA_001 {
        end source : PT_PT_MEA_001;
        end target : ~PT_PT_MEA_001;
        flow of I_ITM_MEA_001 from source.payload to target.payload;
    }
    interface def IF_IF_MEA_002 {
        end source : PT_PT_MEA_002;
        end target : ~PT_PT_MEA_002;
        flow of I_ITM_MEA_002 from source.payload to target.payload;
    }
    interface def IF_IF_MEA_003 {
        end source : PT_PT_MEA_003;
        end target : ~PT_PT_MEA_003;
        flow of I_ITM_MEA_003 from source.payload to target.payload;
    }
    interface def IF_IF_MEA_004 {
        end source : PT_PT_MEA_004;
        end target : ~PT_PT_MEA_004;
        flow of I_ITM_MEA_004 from source.payload to target.payload;
    }
    interface def IF_IF_MEA_005 {
        end source : PT_PT_MEA_005;
        end target : ~PT_PT_MEA_005;
        flow of I_ITM_MEA_005 from source.payload to target.payload;
    }
    interface def IF_IF_MEA_006 {
        end source : PT_PT_MEA_006;
        end target : ~PT_PT_MEA_006;
        flow of I_ITM_MEA_006 from source.payload to target.payload;
    }
    interface def IF_IF_MEA_007 {
        end source : PT_PT_MEA_007;
        end target : ~PT_PT_MEA_007;
        flow of I_ITM_MEA_007 from source.payload to target.payload;
    }
    interface def IF_IF_MEA_008 {
        end source : PT_PT_MEA_008;
        end target : ~PT_PT_MEA_008;
        flow of I_ITM_MEA_008 from source.payload to target.payload;
    }
    interface def IF_IF_MEA_009 {
        end source : PT_PT_MEA_009;
        end target : ~PT_PT_MEA_009;
        flow of I_ITM_MEA_009 from source.payload to target.payload;
    }
    interface def IF_IF_MEA_010 {
        end source : PT_PT_MEA_010;
        end target : ~PT_PT_MEA_010;
        flow of I_ITM_MEA_010 from source.payload to target.payload;
    }
    interface def IF_IF_MEA_011 {
        end source : PT_PT_MEA_011;
        end target : ~PT_PT_MEA_011;
        flow of I_ITM_MEA_011 from source.payload to target.payload;
    }
    interface def IF_IF_MEA_012 {
        end source : PT_PT_MEA_012;
        end target : ~PT_PT_MEA_012;
        flow of I_ITM_MEA_012 from source.payload to target.payload;
    }
    interface def IF_IF_MEA_013 {
        end source : PT_PT_MEA_013;
        end target : ~PT_PT_MEA_013;
        flow of I_ITM_MEA_013 from source.payload to target.payload;
    }
    interface def IF_IF_MEA_014 {
        end source : PT_PT_MEA_014;
        end target : ~PT_PT_MEA_014;
        flow of I_ITM_MEA_014 from source.payload to target.payload;
    }
    interface def IF_IF_MEA_015 {
        end source : PT_PT_MEA_015;
        end target : ~PT_PT_MEA_015;
        flow of I_ITM_MEA_015 from source.payload to target.payload;
    }
    interface def IF_IF_MEA_016 {
        end source : PT_PT_MEA_016;
        end target : ~PT_PT_MEA_016;
        flow of I_ITM_MEA_016 from source.payload to target.payload;
    }
    interface def IF_IF_MEA_017 {
        end source : PT_PT_MEA_017;
        end target : ~PT_PT_MEA_017;
        flow of I_ITM_MEA_017 from source.payload to target.payload;
    }
    interface def IF_IF_MEA_018 {
        end source : PT_PT_MEA_018;
        end target : ~PT_PT_MEA_018;
        flow of I_ITM_MEA_018 from source.payload to target.payload;
    }
    interface def IF_IF_MEA_019 {
        end source : PT_PT_MEA_019;
        end target : ~PT_PT_MEA_019;
        flow of I_ITM_MEA_019 from source.payload to target.payload;
    }
    interface def IF_IF_MEA_020 {
        end source : PT_PT_MEA_020;
        end target : ~PT_PT_MEA_020;
        flow of I_ITM_MEA_020 from source.payload to target.payload;
    }
    interface def IF_IF_MEA_021 {
        end source : PT_PT_MEA_021;
        end target : ~PT_PT_MEA_021;
        flow of I_ITM_MEA_021 from source.payload to target.payload;
    }
    interface def IF_IF_MEA_022 {
        end source : PT_PT_MEA_022;
        end target : ~PT_PT_MEA_022;
        flow of I_ITM_MEA_022 from source.payload to target.payload;
    }
    interface def IF_IF_MEA_023 {
        end source : PT_PT_MEA_023;
        end target : ~PT_PT_MEA_023;
        flow of I_ITM_MEA_023 from source.payload to target.payload;
    }
    interface def IF_IF_MEA_024 {
        end source : PT_PT_MEA_024;
        end target : ~PT_PT_MEA_024;
        flow of I_ITM_MEA_024 from source.payload to target.payload;
    }
    interface def IF_IF_MEA_025 {
        end source : PT_PT_MEA_025;
        end target : ~PT_PT_MEA_025;
        flow of I_ITM_MEA_025 from source.payload to target.payload;
    }
    interface def IF_IF_MEA_026 {
        end source : PT_PT_MEA_026;
        end target : ~PT_PT_MEA_026;
        flow of I_ITM_MEA_026 from source.payload to target.payload;
    }
    interface def IF_IF_MEA_027 {
        end source : PT_PT_MEA_027;
        end target : ~PT_PT_MEA_027;
        flow of I_ITM_MEA_027 from source.payload to target.payload;
    }
    interface def IF_IF_MEA_028 {
        end source : PT_PT_MEA_028;
        end target : ~PT_PT_MEA_028;
        flow of I_ITM_MEA_028 from source.payload to target.payload;
    }
    interface def IF_IF_MEA_029 {
        end source : PT_PT_MEA_029;
        end target : ~PT_PT_MEA_029;
        flow of I_ITM_MEA_029 from source.payload to target.payload;
    }
    interface def IF_IF_MEA_030 {
        end source : PT_PT_MEA_030;
        end target : ~PT_PT_MEA_030;
        flow of I_ITM_MEA_030 from source.payload to target.payload;
    }
    interface def IF_IF_MEA_031 {
        end source : PT_PT_MEA_031;
        end target : ~PT_PT_MEA_031;
        flow of I_ITM_MEA_031 from source.payload to target.payload;
    }
    interface def IF_IF_PHY_001 {
        end source : PT_PT_PHY_001;
        end target : PT_PT_PHY_001;
        flow of I_ITM_PHY_001 from source.payload to target.payload;
    }
    interface def IF_IF_PHY_002 {
        end source : PT_PT_PHY_002;
        end target : PT_PT_PHY_002;
        flow of I_ITM_PHY_002 from source.payload to target.payload;
    }
    interface def IF_IF_PHY_003 {
        end source : PT_PT_PHY_003;
        end target : PT_PT_PHY_003;
        flow of I_ITM_PHY_003 from source.payload to target.payload;
    }
    interface def IF_IF_PHY_004 {
        end source : PT_PT_PHY_004;
        end target : PT_PT_PHY_004;
        flow of I_ITM_PHY_004 from source.payload to target.payload;
    }
    interface def IF_IF_PHY_005 {
        end source : PT_PT_PHY_005;
        end target : PT_PT_PHY_005;
        flow of I_ITM_PHY_005 from source.payload to target.payload;
    }
    interface def IF_IF_PHY_006 {
        end source : PT_PT_PHY_006;
        end target : PT_PT_PHY_006;
        flow of I_ITM_PHY_006 from source.payload to target.payload;
    }
    interface def IF_IF_PHY_007 {
        end source : PT_PT_PHY_007;
        end target : PT_PT_PHY_007;
        flow of I_ITM_PHY_007 from source.payload to target.payload;
    }
    interface def IF_IF_PHY_008 {
        end source : PT_PT_PHY_008;
        end target : PT_PT_PHY_008;
        flow of I_ITM_PHY_008 from source.payload to target.payload;
    }
    interface def IF_IF_PHY_009 {
        end source : PT_PT_PHY_009;
        end target : PT_PT_PHY_009;
        flow of I_ITM_PHY_009 from source.payload to target.payload;
    }
    interface def IF_IF_PHY_010 {
        end source : PT_PT_PHY_010;
        end target : PT_PT_PHY_010;
        flow of I_ITM_PHY_010 from source.payload to target.payload;
    }
    interface def IF_IF_PHY_011 {
        end source : PT_PT_PHY_011;
        end target : PT_PT_PHY_011;
        flow of I_ITM_PHY_011 from source.payload to target.payload;
    }
    interface def IF_IF_PHY_012 {
        end source : PT_PT_PHY_012;
        end target : PT_PT_PHY_012;
        flow of I_ITM_PHY_012 from source.payload to target.payload;
    }
    interface def IF_IF_PHY_013 {
        end source : PT_PT_PHY_013;
        end target : PT_PT_PHY_013;
        flow of I_ITM_PHY_013 from source.payload to target.payload;
    }
    interface def IF_IF_PHY_014 {
        end source : PT_PT_PHY_014;
        end target : PT_PT_PHY_014;
        flow of I_ITM_PHY_014 from source.payload to target.payload;
    }
    interface def IF_IF_PHY_015 {
        end source : PT_PT_PHY_015;
        end target : PT_PT_PHY_015;
        flow of I_ITM_PHY_015 from source.payload to target.payload;
    }
    interface def IF_IF_PHY_016 {
        end source : PT_PT_PHY_016;
        end target : PT_PT_PHY_016;
        flow of I_ITM_PHY_016 from source.payload to target.payload;
    }
    interface def IF_IF_STA_001 {
        end source : PT_PT_STA_001;
        end target : ~PT_PT_STA_001;
        flow of I_ITM_STA_001 from source.payload to target.payload;
    }
    interface def IF_IF_STA_002 {
        end source : PT_PT_STA_002;
        end target : ~PT_PT_STA_002;
        flow of I_ITM_STA_002 from source.payload to target.payload;
    }
    interface def IF_IF_STA_003 {
        end source : PT_PT_STA_003;
        end target : ~PT_PT_STA_003;
        flow of I_ITM_STA_003 from source.payload to target.payload;
    }
    interface def IF_IF_STA_004 {
        end source : PT_PT_STA_004;
        end target : ~PT_PT_STA_004;
        flow of I_ITM_STA_004 from source.payload to target.payload;
    }
    interface def IF_IF_STA_005 {
        end source : PT_PT_STA_005;
        end target : ~PT_PT_STA_005;
        flow of I_ITM_STA_005 from source.payload to target.payload;
    }
    interface def IF_IF_STA_006 {
        end source : PT_PT_STA_006;
        end target : ~PT_PT_STA_006;
        flow of I_ITM_STA_006 from source.payload to target.payload;
    }
    interface def IF_IF_STA_007 {
        end source : PT_PT_STA_007;
        end target : ~PT_PT_STA_007;
        flow of I_ITM_STA_007 from source.payload to target.payload;
    }
    interface def IF_IF_STA_008 {
        end source : PT_PT_STA_008;
        end target : ~PT_PT_STA_008;
        flow of I_ITM_STA_008 from source.payload to target.payload;
    }
    interface def IF_IF_STA_009 {
        end source : PT_PT_STA_009;
        end target : ~PT_PT_STA_009;
        flow of I_ITM_STA_009 from source.payload to target.payload;
    }
    interface def IF_IF_STA_010 {
        end source : PT_PT_STA_010;
        end target : ~PT_PT_STA_010;
        flow of I_ITM_STA_010 from source.payload to target.payload;
    }
    interface def IF_IF_STA_011 {
        end source : PT_PT_STA_011;
        end target : ~PT_PT_STA_011;
        flow of I_ITM_STA_011 from source.payload to target.payload;
    }
    interface def IF_IF_STA_012 {
        end source : PT_PT_STA_012;
        end target : ~PT_PT_STA_012;
        flow of I_ITM_STA_012 from source.payload to target.payload;
    }
    interface def IF_IF_STA_013 {
        end source : PT_PT_STA_013;
        end target : ~PT_PT_STA_013;
        flow of I_ITM_STA_013 from source.payload to target.payload;
    }
    interface def IF_IF_STA_014 {
        end source : PT_PT_STA_014;
        end target : ~PT_PT_STA_014;
        flow of I_ITM_STA_014 from source.payload to target.payload;
    }
    interface def IF_IF_STA_015 {
        end source : PT_PT_STA_015;
        end target : ~PT_PT_STA_015;
        flow of I_ITM_STA_015 from source.payload to target.payload;
    }
    interface def IF_IF_STA_016 {
        end source : PT_PT_STA_016;
        end target : ~PT_PT_STA_016;
        flow of I_ITM_STA_016 from source.payload to target.payload;
    }
    interface def IF_IF_STA_017 {
        end source : PT_PT_STA_017;
        end target : ~PT_PT_STA_017;
        flow of I_ITM_STA_017 from source.payload to target.payload;
    }
    interface def IF_IF_STA_018 {
        end source : PT_PT_STA_018;
        end target : ~PT_PT_STA_018;
        flow of I_ITM_STA_018 from source.payload to target.payload;
    }
    interface def IF_IF_STA_019 {
        end source : PT_PT_STA_019;
        end target : ~PT_PT_STA_019;
        flow of I_ITM_STA_019 from source.payload to target.payload;
    }
    interface def IF_IF_STA_020 {
        end source : PT_PT_STA_020;
        end target : ~PT_PT_STA_020;
        flow of I_ITM_STA_020 from source.payload to target.payload;
    }
    interface def IF_IF_STA_021 {
        end source : PT_PT_STA_021;
        end target : ~PT_PT_STA_021;
        flow of I_ITM_STA_021 from source.payload to target.payload;
    }
    interface def IF_IF_STA_022 {
        end source : PT_PT_STA_022;
        end target : ~PT_PT_STA_022;
        flow of I_ITM_STA_022 from source.payload to target.payload;
    }
    interface def IF_IF_STA_023 {
        end source : PT_PT_STA_023;
        end target : ~PT_PT_STA_023;
        flow of I_ITM_STA_023 from source.payload to target.payload;
    }
    interface def IF_IF_STA_024 {
        end source : PT_PT_STA_024;
        end target : ~PT_PT_STA_024;
        flow of I_ITM_STA_024 from source.payload to target.payload;
    }
    interface def IF_IF_STA_025 {
        end source : PT_PT_STA_025;
        end target : ~PT_PT_STA_025;
        flow of I_ITM_STA_025 from source.payload to target.payload;
    }
    interface def IF_IF_STA_026 {
        end source : PT_PT_STA_026;
        end target : ~PT_PT_STA_026;
        flow of I_ITM_STA_026 from source.payload to target.payload;
    }
    interface def IF_IF_STA_027 {
        end source : PT_PT_STA_027;
        end target : ~PT_PT_STA_027;
        flow of I_ITM_STA_027 from source.payload to target.payload;
    }
    interface def IF_IF_STA_028 {
        end source : PT_PT_STA_028;
        end target : ~PT_PT_STA_028;
        flow of I_ITM_STA_028 from source.payload to target.payload;
    }
    interface def IF_IF_STA_029 {
        end source : PT_PT_STA_029;
        end target : ~PT_PT_STA_029;
        flow of I_ITM_STA_029 from source.payload to target.payload;
    }
    interface def IF_IF_STA_030 {
        end source : PT_PT_STA_030;
        end target : ~PT_PT_STA_030;
        flow of I_ITM_STA_030 from source.payload to target.payload;
    }
    interface def IF_IF_STA_031 {
        end source : PT_PT_STA_031;
        end target : ~PT_PT_STA_031;
        flow of I_ITM_STA_031 from source.payload to target.payload;
    }
    interface def IF_IF_STA_032 {
        end source : PT_PT_STA_032;
        end target : ~PT_PT_STA_032;
        flow of I_ITM_STA_032 from source.payload to target.payload;
    }
    interface def IF_IF_STA_033 {
        end source : PT_PT_STA_033;
        end target : ~PT_PT_STA_033;
        flow of I_ITM_STA_033 from source.payload to target.payload;
    }
    interface def IF_IF_STA_034 {
        end source : PT_PT_STA_034;
        end target : ~PT_PT_STA_034;
        flow of I_ITM_STA_034 from source.payload to target.payload;
    }
    interface def IF_IF_STA_035 {
        end source : PT_PT_STA_035;
        end target : ~PT_PT_STA_035;
        flow of I_ITM_STA_035 from source.payload to target.payload;
    }
    interface def IF_IF_STA_036 {
        end source : PT_PT_STA_036;
        end target : ~PT_PT_STA_036;
        flow of I_ITM_STA_036 from source.payload to target.payload;
    }
}
