package GeneralDefinitions {
    private import ScalarValues::*;
    part def ExternalBoundaryBase {
        attribute sourceType : String = "external_boundary";
    }
}

package ItemDefinitions {
    private import ScalarValues::*;
    item def I_ITM_ACC_001 {
        attribute itemCode : String = "ITM-ACC-001";
        attribute chineseName : String = "牵引实际功率";
        attribute englishName : String = "TractionPowerActual";
        attribute family : String = "能量统计";
        attribute domain : String = "能量统计";
        attribute datatype : String = "Real";
        attribute unitOrMedium : String = "W";
        attribute semanticDefinition : String = "车辆牵引工况实际消耗的牵引功率。";
        attribute aliases : String = "P_trac";
        attribute priority : String = "监测";
        attribute validityRule : String = "积分窗口/符号约定/初值必须固定";
        attribute faultStrategy : String = "DiagnosticOnly";
    }
    item def I_ITM_ACC_002 {
        attribute itemCode : String = "ITM-ACC-002";
        attribute chineseName : String = "实际再生功率";
        attribute englishName : String = "RegenerativePowerActual";
        attribute family : String = "能量统计";
        attribute domain : String = "能量统计";
        attribute datatype : String = "Real";
        attribute unitOrMedium : String = "W";
        attribute semanticDefinition : String = "制动过程中牵引电机/变流器实际产生的再生电功率。";
        attribute aliases : String = "P_reg_actual;再生功率";
        attribute priority : String = "核心";
        attribute validityRule : String = "积分窗口/符号约定/初值必须固定";
        attribute faultStrategy : String = "DiagnosticOnly";
    }
    item def I_ITM_ACC_003 {
        attribute itemCode : String = "ITM-ACC-003";
        attribute chineseName : String = "回馈电网功率";
        attribute englishName : String = "GridReturnedPower";
        attribute family : String = "能量统计";
        attribute domain : String = "能量统计";
        attribute datatype : String = "Real";
        attribute unitOrMedium : String = "W";
        attribute semanticDefinition : String = "实际回馈至外部供电网络的电功率。";
        attribute aliases : String = "P_grid_return;回馈功率";
        attribute priority : String = "核心";
        attribute validityRule : String = "积分窗口/符号约定/初值必须固定";
        attribute faultStrategy : String = "DiagnosticOnly";
    }
    item def I_ITM_ACC_004 {
        attribute itemCode : String = "ITM-ACC-004";
        attribute chineseName : String = "储能吸收功率";
        attribute englishName : String = "ESSAbsorbedPower";
        attribute family : String = "能量统计";
        attribute domain : String = "能量统计";
        attribute datatype : String = "Real";
        attribute unitOrMedium : String = "W";
        attribute semanticDefinition : String = "超级电容储能支路实际吸收的再生功率。";
        attribute aliases : String = "P_ESS_absorb";
        attribute priority : String = "核心";
        attribute validityRule : String = "积分窗口/符号约定/初值必须固定";
        attribute faultStrategy : String = "DiagnosticOnly";
    }
    item def I_ITM_ACC_005 {
        attribute itemCode : String = "ITM-ACC-005";
        attribute chineseName : String = "制动电阻耗散功率";
        attribute englishName : String = "BrakeResistorDissipatedPower";
        attribute family : String = "能量统计";
        attribute domain : String = "能量统计";
        attribute datatype : String = "Real";
        attribute unitOrMedium : String = "W";
        attribute semanticDefinition : String = "制动电阻实际耗散功率。";
        attribute aliases : String = "P_rheo;电阻耗散功率";
        attribute priority : String = "核心";
        attribute validityRule : String = "积分窗口/符号约定/初值必须固定";
        attribute faultStrategy : String = "DiagnosticOnly";
    }
    item def I_ITM_ACC_006 {
        attribute itemCode : String = "ITM-ACC-006";
        attribute chineseName : String = "摩擦制动耗散功率";
        attribute englishName : String = "FrictionBrakeDissipatedPower";
        attribute family : String = "能量统计";
        attribute domain : String = "能量统计";
        attribute datatype : String = "Real";
        attribute unitOrMedium : String = "W";
        attribute semanticDefinition : String = "摩擦制动通道实际耗散的机械功率。";
        attribute aliases : String = "P_friction";
        attribute priority : String = "条件";
        attribute validityRule : String = "积分窗口/符号约定/初值必须固定";
        attribute faultStrategy : String = "DiagnosticOnly";
    }
    item def I_ITM_ACC_007 {
        attribute itemCode : String = "ITM-ACC-007";
        attribute chineseName : String = "牵引累计能量";
        attribute englishName : String = "TractionEnergyConsumed";
        attribute family : String = "能量统计";
        attribute domain : String = "能量统计";
        attribute datatype : String = "Real";
        attribute unitOrMedium : String = "J";
        attribute semanticDefinition : String = "牵引阶段累计消耗的电能。";
        attribute aliases : String = "E_trac";
        attribute priority : String = "监测";
        attribute validityRule : String = "积分窗口/符号约定/初值必须固定";
        attribute faultStrategy : String = "DiagnosticOnly";
    }
    item def I_ITM_ACC_008 {
        attribute itemCode : String = "ITM-ACC-008";
        attribute chineseName : String = "再生发电累计能量";
        attribute englishName : String = "RegenerativeEnergyGenerated";
        attribute family : String = "能量统计";
        attribute domain : String = "能量统计";
        attribute datatype : String = "Real";
        attribute unitOrMedium : String = "J";
        attribute semanticDefinition : String = "电制动实际转换得到的累计再生电能。";
        attribute aliases : String = "E_regen;再生能量";
        attribute priority : String = "核心";
        attribute validityRule : String = "积分窗口/符号约定/初值必须固定";
        attribute faultStrategy : String = "DiagnosticOnly";
    }
    item def I_ITM_ACC_009 {
        attribute itemCode : String = "ITM-ACC-009";
        attribute chineseName : String = "回馈电网累计能量";
        attribute englishName : String = "GridReturnedEnergy";
        attribute family : String = "能量统计";
        attribute domain : String = "能量统计";
        attribute datatype : String = "Real";
        attribute unitOrMedium : String = "J";
        attribute semanticDefinition : String = "实际回馈到供电网络的累计能量。";
        attribute aliases : String = "E_grid_return";
        attribute priority : String = "核心";
        attribute validityRule : String = "积分窗口/符号约定/初值必须固定";
        attribute faultStrategy : String = "DiagnosticOnly";
    }
    item def I_ITM_ACC_010 {
        attribute itemCode : String = "ITM-ACC-010";
        attribute chineseName : String = "储能吸收累计能量";
        attribute englishName : String = "ESSAbsorbedEnergy";
        attribute family : String = "能量统计";
        attribute domain : String = "能量统计";
        attribute datatype : String = "Real";
        attribute unitOrMedium : String = "J";
        attribute semanticDefinition : String = "超级电容储能支路累计吸收的再生能量。";
        attribute aliases : String = "E_ESS_absorb;SC absorbed energy";
        attribute priority : String = "核心";
        attribute validityRule : String = "积分窗口/符号约定/初值必须固定";
        attribute faultStrategy : String = "DiagnosticOnly";
    }
    item def I_ITM_ACC_011 {
        attribute itemCode : String = "ITM-ACC-011";
        attribute chineseName : String = "储能释放累计能量";
        attribute englishName : String = "ESSDischargedEnergy";
        attribute family : String = "能量统计";
        attribute domain : String = "能量统计";
        attribute datatype : String = "Real";
        attribute unitOrMedium : String = "J";
        attribute semanticDefinition : String = "超级电容向直流母线累计释放的能量。";
        attribute aliases : String = "E_ESS_discharge";
        attribute priority : String = "监测";
        attribute validityRule : String = "积分窗口/符号约定/初值必须固定";
        attribute faultStrategy : String = "DiagnosticOnly";
    }
    item def I_ITM_ACC_012 {
        attribute itemCode : String = "ITM-ACC-012";
        attribute chineseName : String = "制动电阻耗散累计能量";
        attribute englishName : String = "BrakeResistorDissipatedEnergy";
        attribute family : String = "能量统计";
        attribute domain : String = "能量统计";
        attribute datatype : String = "Real";
        attribute unitOrMedium : String = "J";
        attribute semanticDefinition : String = "制动电阻累计耗散的电能。";
        attribute aliases : String = "E_rheo";
        attribute priority : String = "核心";
        attribute validityRule : String = "积分窗口/符号约定/初值必须固定";
        attribute faultStrategy : String = "DiagnosticOnly";
    }
    item def I_ITM_ACC_013 {
        attribute itemCode : String = "ITM-ACC-013";
        attribute chineseName : String = "摩擦制动耗散累计能量";
        attribute englishName : String = "FrictionBrakeDissipatedEnergy";
        attribute family : String = "能量统计";
        attribute domain : String = "能量统计";
        attribute datatype : String = "Real";
        attribute unitOrMedium : String = "J";
        attribute semanticDefinition : String = "摩擦制动累计耗散的机械能。";
        attribute aliases : String = "E_friction";
        attribute priority : String = "条件";
        attribute validityRule : String = "积分窗口/符号约定/初值必须固定";
        attribute faultStrategy : String = "DiagnosticOnly";
    }
    item def I_ITM_ACC_014 {
        attribute itemCode : String = "ITM-ACC-014";
        attribute chineseName : String = "可用制动能量";
        attribute englishName : String = "AvailableBrakingEnergy";
        attribute family : String = "能量统计";
        attribute domain : String = "能量统计";
        attribute datatype : String = "Real";
        attribute unitOrMedium : String = "J";
        attribute semanticDefinition : String = "用于能量回收率评价的理论/基准可用制动能量,定义必须在验证方案中固定。";
        attribute aliases : String = "E_brake_available;理论制动能量";
        attribute priority : String = "核心";
        attribute validityRule : String = "积分窗口/符号约定/初值必须固定";
        attribute faultStrategy : String = "DiagnosticOnly";
    }
    item def I_ITM_ACC_015 {
        attribute itemCode : String = "ITM-ACC-015";
        attribute chineseName : String = "能量回收率";
        attribute englishName : String = "EnergyRecoveryRatio";
        attribute family : String = "能量统计";
        attribute domain : String = "能量统计";
        attribute datatype : String = "Real";
        attribute unitOrMedium : String = "1";
        attribute semanticDefinition : String = "按项目统一分母定义计算的有效再生能量回收比例。";
        attribute aliases : String = "回收效率;回收率";
        attribute priority : String = "监测";
        attribute validityRule : String = "积分窗口/符号约定/初值必须固定";
        attribute faultStrategy : String = "DiagnosticOnly";
    }
    item def I_ITM_CMD_001 {
        attribute itemCode : String = "ITM-CMD-001";
        attribute chineseName : String = "列车方向指令";
        attribute englishName : String = "TrainDirectionCommand";
        attribute family : String = "命令/请求";
        attribute domain : String = "驾驶/控制";
        attribute datatype : String = "Enum";
        attribute unitOrMedium : String = "无";
        attribute semanticDefinition : String = "司机或控制系统给出的列车运行方向选择。";
        attribute aliases : String = "方向指令;前进后退";
        attribute priority : String = "核心";
        attribute validityRule : String = "应包含有效位/时效性/范围检查";
        attribute faultStrategy : String = "RejectStale+SafeFallback";
    }
    item def I_ITM_CMD_002 {
        attribute itemCode : String = "ITM-CMD-002";
        attribute chineseName : String = "牵引指令";
        attribute englishName : String = "TractionCommand";
        attribute family : String = "命令/请求";
        attribute domain : String = "驾驶/牵引";
        attribute datatype : String = "Real";
        attribute unitOrMedium : String = "1";
        attribute semanticDefinition : String = "司机/ATO等给出的归一化牵引需求。";
        attribute aliases : String = "牵引级位;牵引需求";
        attribute priority : String = "核心";
        attribute validityRule : String = "应包含有效位/时效性/范围检查";
        attribute faultStrategy : String = "RejectStale+SafeFallback";
    }
    item def I_ITM_CMD_003 {
        attribute itemCode : String = "ITM-CMD-003";
        attribute chineseName : String = "服务制动请求";
        attribute englishName : String = "ServiceBrakeRequest";
        attribute family : String = "命令/请求";
        attribute domain : String = "制动";
        attribute datatype : String = "Real";
        attribute unitOrMedium : String = "1 或 m/s2";
        attribute semanticDefinition : String = "服务制动需求;可采用归一化请求或减速度请求,工程中必须在接口处固定一种语义。";
        attribute aliases : String = "常用制动请求;制动级位;服务制动减速度请求";
        attribute priority : String = "核心";
        attribute validityRule : String = "应包含有效位/时效性/范围检查";
        attribute faultStrategy : String = "RejectStale+SafeFallback";
    }
    item def I_ITM_CMD_004 {
        attribute itemCode : String = "ITM-CMD-004";
        attribute chineseName : String = "紧急制动请求";
        attribute englishName : String = "EmergencyBrakeRequest";
        attribute family : String = "命令/请求";
        attribute domain : String = "制动";
        attribute datatype : String = "Boolean";
        attribute unitOrMedium : String = "无";
        attribute semanticDefinition : String = "触发紧急制动的有效请求。";
        attribute aliases : String = "EB请求;紧急制动命令";
        attribute priority : String = "核心";
        attribute validityRule : String = "应包含有效位/时效性/范围检查";
        attribute faultStrategy : String = "RejectStale+SafeFallback";
    }
    item def I_ITM_CMD_005 {
        attribute itemCode : String = "ITM-CMD-005";
        attribute chineseName : String = "总制动力请求";
        attribute englishName : String = "TotalBrakeForceRequest";
        attribute family : String = "命令/请求";
        attribute domain : String = "制动";
        attribute datatype : String = "Real";
        attribute unitOrMedium : String = "N";
        attribute semanticDefinition : String = "由制动控制根据服务/紧急请求、质量和运行状态形成的列车总制动力需求。";
        attribute aliases : String = "总制动力指令;列车制动力需求";
        attribute priority : String = "核心";
        attribute validityRule : String = "应包含有效位/时效性/范围检查";
        attribute faultStrategy : String = "RejectStale+SafeFallback";
    }
    item def I_ITM_CMD_006 {
        attribute itemCode : String = "ITM-CMD-006";
        attribute chineseName : String = "动态制动力请求";
        attribute englishName : String = "DynamicBrakeForceRequest";
        attribute family : String = "命令/请求";
        attribute domain : String = "牵引/制动";
        attribute datatype : String = "Real";
        attribute unitOrMedium : String = "N";
        attribute semanticDefinition : String = "分配给牵引电制动通道的动态制动力请求。";
        attribute aliases : String = "电制动力请求;再生制动力请求";
        attribute priority : String = "核心";
        attribute validityRule : String = "应包含有效位/时效性/范围检查";
        attribute faultStrategy : String = "RejectStale+SafeFallback";
    }
    item def I_ITM_CMD_007 {
        attribute itemCode : String = "ITM-CMD-007";
        attribute chineseName : String = "摩擦制动力请求";
        attribute englishName : String = "FrictionBrakeForceRequest";
        attribute family : String = "命令/请求";
        attribute domain : String = "制动";
        attribute datatype : String = "Real";
        attribute unitOrMedium : String = "N";
        attribute semanticDefinition : String = "分配给摩擦制动通道的制动力请求。";
        attribute aliases : String = "机械制动力请求;空气制动力请求";
        attribute priority : String = "核心";
        attribute validityRule : String = "应包含有效位/时效性/范围检查";
        attribute faultStrategy : String = "RejectStale+SafeFallback";
    }
    item def I_ITM_CMD_008 {
        attribute itemCode : String = "ITM-CMD-008";
        attribute chineseName : String = "牵引切除请求";
        attribute englishName : String = "TractionCutOffRequest";
        attribute family : String = "命令/请求";
        attribute domain : String = "牵引/制动";
        attribute datatype : String = "Boolean";
        attribute unitOrMedium : String = "无";
        attribute semanticDefinition : String = "制动或安全功能要求牵引系统禁止输出牵引力的请求。";
        attribute aliases : String = "牵引封锁;牵引切断命令";
        attribute priority : String = "核心";
        attribute validityRule : String = "应包含有效位/时效性/范围检查";
        attribute faultStrategy : String = "RejectStale+SafeFallback";
    }
    item def I_ITM_CMD_009 {
        attribute itemCode : String = "ITM-CMD-009";
        attribute chineseName : String = "牵引使能指令";
        attribute englishName : String = "TractionEnableCommand";
        attribute family : String = "命令/请求";
        attribute domain : String = "牵引";
        attribute datatype : String = "Boolean";
        attribute unitOrMedium : String = "无";
        attribute semanticDefinition : String = "允许牵引控制进入可输出牵引转矩状态的指令。";
        attribute aliases : String = "牵引允许;牵引使能";
        attribute priority : String = "核心";
        attribute validityRule : String = "应包含有效位/时效性/范围检查";
        attribute faultStrategy : String = "RejectStale+SafeFallback";
    }
    item def I_ITM_CMD_010 {
        attribute itemCode : String = "ITM-CMD-010";
        attribute chineseName : String = "网侧变流控制指令";
        attribute englishName : String = "GridSideConverterCommand";
        attribute family : String = "命令/请求";
        attribute domain : String = "牵引";
        attribute datatype : String = "ControlVector";
        attribute unitOrMedium : String = "无";
        attribute semanticDefinition : String = "网侧变流器控制模块向网侧功率模块发出的规范化控制指令;实现可映射为PWM、dq电流或功率控制量。";
        attribute aliases : String = "网侧PWM;网侧电流指令;网侧功率指令";
        attribute priority : String = "核心";
        attribute validityRule : String = "应包含有效位/时效性/范围检查";
        attribute faultStrategy : String = "RejectStale+SafeFallback";
    }
    item def I_ITM_CMD_011 {
        attribute itemCode : String = "ITM-CMD-011";
        attribute chineseName : String = "电机侧变流控制指令";
        attribute englishName : String = "MotorSideConverterCommand";
        attribute family : String = "命令/请求";
        attribute domain : String = "牵引";
        attribute datatype : String = "ControlVector";
        attribute unitOrMedium : String = "无";
        attribute semanticDefinition : String = "电机侧控制模块向电机侧功率模块发出的规范化控制指令。";
        attribute aliases : String = "逆变器控制指令;电机侧PWM;dq控制指令";
        attribute priority : String = "核心";
        attribute validityRule : String = "应包含有效位/时效性/范围检查";
        attribute faultStrategy : String = "RejectStale+SafeFallback";
    }
    item def I_ITM_CMD_012 {
        attribute itemCode : String = "ITM-CMD-012";
        attribute chineseName : String = "牵引电机转矩请求";
        attribute englishName : String = "MotorTorqueRequest";
        attribute family : String = "命令/请求";
        attribute domain : String = "牵引";
        attribute datatype : String = "Real";
        attribute unitOrMedium : String = "N·m";
        attribute semanticDefinition : String = "牵引控制向电机控制通道给出的目标电磁转矩;再生制动时符号表示制动方向。";
        attribute aliases : String = "电机转矩指令;转矩给定";
        attribute priority : String = "核心";
        attribute validityRule : String = "应包含有效位/时效性/范围检查";
        attribute faultStrategy : String = "RejectStale+SafeFallback";
    }
    item def I_ITM_CMD_013 {
        attribute itemCode : String = "ITM-CMD-013";
        attribute chineseName : String = "预充电指令";
        attribute englishName : String = "TractionPrechargeCommand";
        attribute family : String = "命令/请求";
        attribute domain : String = "牵引";
        attribute datatype : String = "Boolean";
        attribute unitOrMedium : String = "无";
        attribute semanticDefinition : String = "牵引主回路预充电组件的投入/退出控制请求。";
        attribute aliases : String = "预充电命令";
        attribute priority : String = "核心";
        attribute validityRule : String = "应包含有效位/时效性/范围检查";
        attribute faultStrategy : String = "RejectStale+SafeFallback";
    }
    item def I_ITM_CMD_014 {
        attribute itemCode : String = "ITM-CMD-014";
        attribute chineseName : String = "牵引输入接通指令";
        attribute englishName : String = "TractionInputConnectCommand";
        attribute family : String = "命令/请求";
        attribute domain : String = "牵引";
        attribute datatype : String = "Boolean";
        attribute unitOrMedium : String = "无";
        attribute semanticDefinition : String = "牵引变流器输入主回路接通/断开的控制请求。";
        attribute aliases : String = "输入接触器命令;主回路接通命令";
        attribute priority : String = "核心";
        attribute validityRule : String = "应包含有效位/时效性/范围检查";
        attribute faultStrategy : String = "RejectStale+SafeFallback";
    }
    item def I_ITM_CMD_015 {
        attribute itemCode : String = "ITM-CMD-015";
        attribute chineseName : String = "制动斩波器指令";
        attribute englishName : String = "BrakeChopperCommand";
        attribute family : String = "命令/请求";
        attribute domain : String = "牵引/能量";
        attribute datatype : String = "Real 或 Boolean";
        attribute unitOrMedium : String = "1/无";
        attribute semanticDefinition : String = "根据直流母线电压与剩余再生功率控制制动电阻支路投入的指令。";
        attribute aliases : String = "放电电阻控制;斩波器占空比";
        attribute priority : String = "核心";
        attribute validityRule : String = "应包含有效位/时效性/范围检查";
        attribute faultStrategy : String = "RejectStale+SafeFallback";
    }
    item def I_ITM_CMD_016 {
        attribute itemCode : String = "ITM-CMD-016";
        attribute chineseName : String = "高压断路器指令";
        attribute englishName : String = "HVBreakerCommand";
        attribute family : String = "命令/请求";
        attribute domain : String = "主供电";
        attribute datatype : String = "Enum";
        attribute unitOrMedium : String = "无";
        attribute semanticDefinition : String = "高压断路器分/合控制请求。";
        attribute aliases : String = "VCB命令;主断命令";
        attribute priority : String = "条件";
        attribute validityRule : String = "应包含有效位/时效性/范围检查";
        attribute faultStrategy : String = "RejectStale+SafeFallback";
    }
    item def I_ITM_CMD_017 {
        attribute itemCode : String = "ITM-CMD-017";
        attribute chineseName : String = "高压隔离开关指令";
        attribute englishName : String = "HVIsolationSwitchCommand";
        attribute family : String = "命令/请求";
        attribute domain : String = "主供电";
        attribute datatype : String = "Enum";
        attribute unitOrMedium : String = "无";
        attribute semanticDefinition : String = "高压隔离开关分/合控制请求。";
        attribute aliases : String = "隔离开关命令";
        attribute priority : String = "条件";
        attribute validityRule : String = "应包含有效位/时效性/范围检查";
        attribute faultStrategy : String = "RejectStale+SafeFallback";
    }
    item def I_ITM_CMD_018 {
        attribute itemCode : String = "ITM-CMD-018";
        attribute chineseName : String = "受电弓控制指令";
        attribute englishName : String = "PantographCommand";
        attribute family : String = "命令/请求";
        attribute domain : String = "主供电";
        attribute datatype : String = "Enum";
        attribute unitOrMedium : String = "无";
        attribute semanticDefinition : String = "受电弓升弓/降弓控制请求。";
        attribute aliases : String = "升弓命令;降弓命令";
        attribute priority : String = "条件";
        attribute validityRule : String = "应包含有效位/时效性/范围检查";
        attribute faultStrategy : String = "RejectStale+SafeFallback";
    }
    item def I_ITM_CMD_019 {
        attribute itemCode : String = "ITM-CMD-019";
        attribute chineseName : String = "制动缓解指令";
        attribute englishName : String = "BrakeReleaseCommand";
        attribute family : String = "命令/请求";
        attribute domain : String = "制动";
        attribute datatype : String = "Boolean";
        attribute unitOrMedium : String = "无";
        attribute semanticDefinition : String = "命令制动执行通道释放已施加制动力。";
        attribute aliases : String = "缓解命令;制动释放";
        attribute priority : String = "核心";
        attribute validityRule : String = "应包含有效位/时效性/范围检查";
        attribute faultStrategy : String = "RejectStale+SafeFallback";
    }
    item def I_ITM_CMD_020 {
        attribute itemCode : String = "ITM-CMD-020";
        attribute chineseName : String = "制动隔离指令";
        attribute englishName : String = "BrakeIsolationCommand";
        attribute family : String = "命令/请求";
        attribute domain : String = "制动";
        attribute datatype : String = "Boolean";
        attribute unitOrMedium : String = "无";
        attribute semanticDefinition : String = "对指定制动通道执行隔离/恢复的控制请求。";
        attribute aliases : String = "截断命令;制动隔离";
        attribute priority : String = "条件";
        attribute validityRule : String = "应包含有效位/时效性/范围检查";
        attribute faultStrategy : String = "RejectStale+SafeFallback";
    }
    item def I_ITM_CMD_021 {
        attribute itemCode : String = "ITM-CMD-021";
        attribute chineseName : String = "电空转换阀指令";
        attribute englishName : String = "EPValveCommand";
        attribute family : String = "命令/请求";
        attribute domain : String = "制动";
        attribute datatype : String = "Real";
        attribute unitOrMedium : String = "1 或 Pa";
        attribute semanticDefinition : String = "EBCU向电空转换阀给出的制动压力/开度控制请求。";
        attribute aliases : String = "EP阀命令;制动压力指令";
        attribute priority : String = "核心";
        attribute validityRule : String = "应包含有效位/时效性/范围检查";
        attribute faultStrategy : String = "RejectStale+SafeFallback";
    }
    item def I_ITM_CMD_022 {
        attribute itemCode : String = "ITM-CMD-022";
        attribute chineseName : String = "制动电磁阀指令";
        attribute englishName : String = "BrakeSolenoidValveCommand";
        attribute family : String = "命令/请求";
        attribute domain : String = "制动";
        attribute datatype : String = "Boolean/Enum";
        attribute unitOrMedium : String = "无";
        attribute semanticDefinition : String = "控制制动电磁阀通断或充排气状态的指令。";
        attribute aliases : String = "电磁阀命令";
        attribute priority : String = "核心";
        attribute validityRule : String = "应包含有效位/时效性/范围检查";
        attribute faultStrategy : String = "RejectStale+SafeFallback";
    }
    item def I_ITM_CMD_023 {
        attribute itemCode : String = "ITM-CMD-023";
        attribute chineseName : String = "防滑干预指令";
        attribute englishName : String = "WSPInterventionCommand";
        attribute family : String = "命令/请求";
        attribute domain : String = "低黏着";
        attribute datatype : String = "Enum";
        attribute unitOrMedium : String = "无";
        attribute semanticDefinition : String = "防滑控制对制动压力保持、降低或恢复的干预指令。";
        attribute aliases : String = "WSP命令;防滑阀命令";
        attribute priority : String = "核心";
        attribute validityRule : String = "应包含有效位/时效性/范围检查";
        attribute faultStrategy : String = "RejectStale+SafeFallback";
    }
    item def I_ITM_CMD_024 {
        attribute itemCode : String = "ITM-CMD-024";
        attribute chineseName : String = "撒砂请求";
        attribute englishName : String = "SandingRequest";
        attribute family : String = "命令/请求";
        attribute domain : String = "低黏着";
        attribute datatype : String = "Boolean";
        attribute unitOrMedium : String = "无";
        attribute semanticDefinition : String = "人工或自动发出的撒砂/增粘请求。";
        attribute aliases : String = "撒砂命令;增粘请求";
        attribute priority : String = "条件";
        attribute validityRule : String = "应包含有效位/时效性/范围检查";
        attribute faultStrategy : String = "RejectStale+SafeFallback";
    }
    item def I_ITM_CMD_025 {
        attribute itemCode : String = "ITM-CMD-025";
        attribute chineseName : String = "储能功率请求";
        attribute englishName : String = "ESSPowerRequest";
        attribute family : String = "命令/请求";
        attribute domain : String = "储能";
        attribute datatype : String = "Real";
        attribute unitOrMedium : String = "W";
        attribute semanticDefinition : String = "上层能量管理向双向DC/DC提出的储能支路功率请求;正负号方向必须项目内固定。";
        attribute aliases : String = "P_ESS_cmd;储能充放电功率指令";
        attribute priority : String = "核心";
        attribute validityRule : String = "应包含有效位/时效性/范围检查";
        attribute faultStrategy : String = "RejectStale+SafeFallback";
    }
    item def I_ITM_CMD_026 {
        attribute itemCode : String = "ITM-CMD-026";
        attribute chineseName : String = "双向DC/DC使能";
        attribute englishName : String = "DCDCEnableCommand";
        attribute family : String = "命令/请求";
        attribute domain : String = "储能";
        attribute datatype : String = "Boolean";
        attribute unitOrMedium : String = "无";
        attribute semanticDefinition : String = "允许双向DC/DC进入功率调节状态的控制请求。";
        attribute aliases : String = "DC/DC使能";
        attribute priority : String = "核心";
        attribute validityRule : String = "应包含有效位/时效性/范围检查";
        attribute faultStrategy : String = "RejectStale+SafeFallback";
    }
    item def I_ITM_CMD_027 {
        attribute itemCode : String = "ITM-CMD-027";
        attribute chineseName : String = "储能主接触器指令";
        attribute englishName : String = "ESSContactorCommand";
        attribute family : String = "命令/请求";
        attribute domain : String = "储能";
        attribute datatype : String = "Boolean";
        attribute unitOrMedium : String = "无";
        attribute semanticDefinition : String = "控制储能支路主接触器接通/断开的请求。";
        attribute aliases : String = "储能接触器命令";
        attribute priority : String = "核心";
        attribute validityRule : String = "应包含有效位/时效性/范围检查";
        attribute faultStrategy : String = "RejectStale+SafeFallback";
    }
    item def I_ITM_CMD_028 {
        attribute itemCode : String = "ITM-CMD-028";
        attribute chineseName : String = "储能预充电指令";
        attribute englishName : String = "ESSPrechargeCommand";
        attribute family : String = "命令/请求";
        attribute domain : String = "储能";
        attribute datatype : String = "Boolean";
        attribute unitOrMedium : String = "无";
        attribute semanticDefinition : String = "控制储能支路预充电过程开始/停止的请求。";
        attribute aliases : String = "ESS预充电命令";
        attribute priority : String = "核心";
        attribute validityRule : String = "应包含有效位/时效性/范围检查";
        attribute faultStrategy : String = "RejectStale+SafeFallback";
    }
    item def I_ITM_CMD_029 {
        attribute itemCode : String = "ITM-CMD-029";
        attribute chineseName : String = "储能故障复位指令";
        attribute englishName : String = "ESSFaultResetCommand";
        attribute family : String = "命令/请求";
        attribute domain : String = "储能";
        attribute datatype : String = "Boolean";
        attribute unitOrMedium : String = "无";
        attribute semanticDefinition : String = "在满足复位条件后请求清除储能保护锁存状态。";
        attribute aliases : String = "ESS复位;DC/DC复位";
        attribute priority : String = "条件";
        attribute validityRule : String = "应包含有效位/时效性/范围检查";
        attribute faultStrategy : String = "RejectStale+SafeFallback";
    }
    item def I_ITM_CMD_030 {
        attribute itemCode : String = "ITM-CMD-030";
        attribute chineseName : String = "安全停车/制动请求";
        attribute englishName : String = "SafetyBrakeRequest";
        attribute family : String = "命令/请求";
        attribute domain : String = "安全";
        attribute datatype : String = "Enum";
        attribute unitOrMedium : String = "无";
        attribute semanticDefinition : String = "来自ATP/安全回路等外部安全功能的制动请求,进入EBCU后映射为服务或紧急制动。";
        attribute aliases : String = "ATP制动请求;安全制动命令";
        attribute priority : String = "条件";
        attribute validityRule : String = "应包含有效位/时效性/范围检查";
        attribute faultStrategy : String = "RejectStale+SafeFallback";
    }
    item def I_ITM_CMD_031 {
        attribute itemCode : String = "ITM-CMD-031";
        attribute chineseName : String = "制动控制接触器指令";
        attribute englishName : String = "BrakeControlContactorCommand";
        attribute family : String = "命令/请求";
        attribute domain : String = "制动";
        attribute datatype : String = "Boolean";
        attribute unitOrMedium : String = "无";
        attribute semanticDefinition : String = "控制制动控制接触器接通/断开的请求。";
        attribute aliases : String = "EBCU接触器命令;制动控制供电接通命令";
        attribute priority : String = "条件";
        attribute validityRule : String = "应包含有效位/时效性检查";
        attribute faultStrategy : String = "RejectStale+SafeFallback";
    }
    item def I_ITM_CMD_032 {
        attribute itemCode : String = "ITM-CMD-032";
        attribute chineseName : String = "撒砂执行指令";
        attribute englishName : String = "SandingActuationCommand";
        attribute family : String = "命令/请求";
        attribute domain : String = "低黏着";
        attribute datatype : String = "Boolean/Enum";
        attribute unitOrMedium : String = "无";
        attribute semanticDefinition : String = "撒砂控制单元向撒砂阀板/执行机构发出的执行指令。";
        attribute aliases : String = "撒砂阀命令;增粘执行命令";
        attribute priority : String = "条件";
        attribute validityRule : String = "应包含有效位/时效性检查";
        attribute faultStrategy : String = "RejectStale+SafeFallback";
    }
    item def I_ITM_LIM_001 {
        attribute itemCode : String = "ITM-LIM-001";
        attribute chineseName : String = "可用动态制动力";
        attribute englishName : String = "AvailableDynamicBrakeForce";
        attribute family : String = "能力/限制";
        attribute domain : String = "牵引/制动";
        attribute datatype : String = "Real";
        attribute unitOrMedium : String = "N";
        attribute semanticDefinition : String = "当前速度、电压、黏着、温度和故障条件下动态制动可提供的最大列车等效制动力。";
        attribute aliases : String = "动态制动能力;电制动上限";
        attribute priority : String = "核心";
        attribute validityRule : String = "必须非负且在工程允许范围内;来源失效时能力应保守降级";
        attribute faultStrategy : String = "DegradeAvailability";
    }
    item def I_ITM_LIM_002 {
        attribute itemCode : String = "ITM-LIM-002";
        attribute chineseName : String = "可用摩擦制动力";
        attribute englishName : String = "AvailableFrictionBrakeForce";
        attribute family : String = "能力/限制";
        attribute domain : String = "制动";
        attribute datatype : String = "Real";
        attribute unitOrMedium : String = "N";
        attribute semanticDefinition : String = "当前压力、隔离和故障条件下摩擦制动可提供的最大制动力。";
        attribute aliases : String = "机械制动能力";
        attribute priority : String = "核心";
        attribute validityRule : String = "必须非负且在工程允许范围内;来源失效时能力应保守降级";
        attribute faultStrategy : String = "DegradeAvailability";
    }
    item def I_ITM_LIM_003 {
        attribute itemCode : String = "ITM-LIM-003";
        attribute chineseName : String = "牵引/再生转矩上限";
        attribute englishName : String = "TractionRegenerationTorqueLimit";
        attribute family : String = "能力/限制";
        attribute domain : String = "牵引";
        attribute datatype : String = "Real";
        attribute unitOrMedium : String = "N·m";
        attribute semanticDefinition : String = "牵引电机当前允许的牵引或再生转矩上限。";
        attribute aliases : String = "T_reg_max;电机转矩上限";
        attribute priority : String = "核心";
        attribute validityRule : String = "必须非负且在工程允许范围内;来源失效时能力应保守降级";
        attribute faultStrategy : String = "DegradeAvailability";
    }
    item def I_ITM_LIM_004 {
        attribute itemCode : String = "ITM-LIM-004";
        attribute chineseName : String = "再生功率上限";
        attribute englishName : String = "RegenerativePowerLimit";
        attribute family : String = "能力/限制";
        attribute domain : String = "牵引/能量";
        attribute datatype : String = "Real";
        attribute unitOrMedium : String = "W";
        attribute semanticDefinition : String = "当前牵引电机、变流器、直流母线和能量接收端共同允许的再生功率上限。";
        attribute aliases : String = "P_reg_max;再生功率能力";
        attribute priority : String = "核心";
        attribute validityRule : String = "必须非负且在工程允许范围内;来源失效时能力应保守降级";
        attribute faultStrategy : String = "DegradeAvailability";
    }
    item def I_ITM_LIM_005 {
        attribute itemCode : String = "ITM-LIM-005";
        attribute chineseName : String = "接触网可接收功率";
        attribute englishName : String = "GridAcceptableRegenerativePower";
        attribute family : String = "能力/限制";
        attribute domain : String = "主供电";
        attribute datatype : String = "Real";
        attribute unitOrMedium : String = "W";
        attribute semanticDefinition : String = "外部供电网络在当前状态下允许车辆回馈的最大再生功率。";
        attribute aliases : String = "P_grid_max;网侧受电能力;网侧回馈容量";
        attribute priority : String = "核心";
        attribute validityRule : String = "必须非负且在工程允许范围内;来源失效时能力应保守降级";
        attribute faultStrategy : String = "DegradeAvailability";
    }
    item def I_ITM_LIM_006 {
        attribute itemCode : String = "ITM-LIM-006";
        attribute chineseName : String = "制动电阻可耗散功率";
        attribute englishName : String = "BrakeResistorAvailablePower";
        attribute family : String = "能力/限制";
        attribute domain : String = "牵引/能量";
        attribute datatype : String = "Real";
        attribute unitOrMedium : String = "W";
        attribute semanticDefinition : String = "制动电阻支路在当前温度/保护状态下可安全耗散的功率。";
        attribute aliases : String = "电阻耗散能力";
        attribute priority : String = "条件";
        attribute validityRule : String = "必须非负且在工程允许范围内;来源失效时能力应保守降级";
        attribute faultStrategy : String = "DegradeAvailability";
    }
    item def I_ITM_LIM_007 {
        attribute itemCode : String = "ITM-LIM-007";
        attribute chineseName : String = "直流母线电压上限";
        attribute englishName : String = "DCLinkVoltageUpperLimit";
        attribute family : String = "能力/限制";
        attribute domain : String = "牵引/储能";
        attribute datatype : String = "Real";
        attribute unitOrMedium : String = "V";
        attribute semanticDefinition : String = "控制/保护功能使用的直流母线最高允许电压限制。";
        attribute aliases : String = "Udc_max;母线过压限值";
        attribute priority : String = "核心";
        attribute validityRule : String = "必须非负且在工程允许范围内;来源失效时能力应保守降级";
        attribute faultStrategy : String = "DegradeAvailability";
    }
    item def I_ITM_LIM_008 {
        attribute itemCode : String = "ITM-LIM-008";
        attribute chineseName : String = "可用黏着限制";
        attribute englishName : String = "AvailableAdhesionLimit";
        attribute family : String = "能力/限制";
        attribute domain : String = "低黏着";
        attribute datatype : String = "Real";
        attribute unitOrMedium : String = "1";
        attribute semanticDefinition : String = "可用于限制轮轨牵引/制动力的黏着边界。";
        attribute aliases : String = "黏着上限;mu_limit";
        attribute priority : String = "条件";
        attribute validityRule : String = "必须非负且在工程允许范围内;来源失效时能力应保守降级";
        attribute faultStrategy : String = "DegradeAvailability";
    }
    item def I_ITM_LIM_009 {
        attribute itemCode : String = "ITM-LIM-009";
        attribute chineseName : String = "储能可用充电功率";
        attribute englishName : String = "ESSAvailableChargePower";
        attribute family : String = "能力/限制";
        attribute domain : String = "储能";
        attribute datatype : String = "Real";
        attribute unitOrMedium : String = "W";
        attribute semanticDefinition : String = "由超级电容SOC、电压、温度、DC/DC能力和保护状态计算的最大允许吸收功率。";
        attribute aliases : String = "ESS充电功率上限;P_charge_avail";
        attribute priority : String = "核心";
        attribute validityRule : String = "必须非负且在工程允许范围内;来源失效时能力应保守降级";
        attribute faultStrategy : String = "DegradeAvailability";
    }
    item def I_ITM_LIM_010 {
        attribute itemCode : String = "ITM-LIM-010";
        attribute chineseName : String = "储能可用放电功率";
        attribute englishName : String = "ESSAvailableDischargePower";
        attribute family : String = "能力/限制";
        attribute domain : String = "储能";
        attribute datatype : String = "Real";
        attribute unitOrMedium : String = "W";
        attribute semanticDefinition : String = "储能支路当前最大允许释放功率。";
        attribute aliases : String = "ESS放电功率上限;P_discharge_avail";
        attribute priority : String = "条件";
        attribute validityRule : String = "必须非负且在工程允许范围内;来源失效时能力应保守降级";
        attribute faultStrategy : String = "DegradeAvailability";
    }
    item def I_ITM_LIM_011 {
        attribute itemCode : String = "ITM-LIM-011";
        attribute chineseName : String = "超级电容充电允许状态";
        attribute englishName : String = "SuperCapChargeAllowed";
        attribute family : String = "能力/限制";
        attribute domain : String = "储能";
        attribute datatype : String = "Boolean";
        attribute unitOrMedium : String = "无";
        attribute semanticDefinition : String = "SOC、电压、温度和故障条件综合判定后的充电许可。";
        attribute aliases : String = "SC charge enable";
        attribute priority : String = "核心";
        attribute validityRule : String = "必须非负且在工程允许范围内;来源失效时能力应保守降级";
        attribute faultStrategy : String = "DegradeAvailability";
    }
    item def I_ITM_LIM_012 {
        attribute itemCode : String = "ITM-LIM-012";
        attribute chineseName : String = "超级电容放电允许状态";
        attribute englishName : String = "SuperCapDischargeAllowed";
        attribute family : String = "能力/限制";
        attribute domain : String = "储能";
        attribute datatype : String = "Boolean";
        attribute unitOrMedium : String = "无";
        attribute semanticDefinition : String = "储能状态和故障条件综合判定后的放电许可。";
        attribute aliases : String = "SC discharge enable";
        attribute priority : String = "条件";
        attribute validityRule : String = "必须非负且在工程允许范围内;来源失效时能力应保守降级";
        attribute faultStrategy : String = "DegradeAvailability";
    }
    item def I_ITM_LIM_013 {
        attribute itemCode : String = "ITM-LIM-013";
        attribute chineseName : String = "最大允许制动力";
        attribute englishName : String = "MaximumAllowedBrakeForce";
        attribute family : String = "能力/限制";
        attribute domain : String = "制动";
        attribute datatype : String = "Real";
        attribute unitOrMedium : String = "N";
        attribute semanticDefinition : String = "由车辆、轨道、舒适性和设备能力共同限定的总制动力上限。";
        attribute aliases : String = "最大制动力";
        attribute priority : String = "条件";
        attribute validityRule : String = "必须非负且在工程允许范围内;来源失效时能力应保守降级";
        attribute faultStrategy : String = "DegradeAvailability";
    }
    item def I_ITM_LIM_014 {
        attribute itemCode : String = "ITM-LIM-014";
        attribute chineseName : String = "最大允许减速度";
        attribute englishName : String = "MaximumAllowedDeceleration";
        attribute family : String = "能力/限制";
        attribute domain : String = "制动";
        attribute datatype : String = "Real";
        attribute unitOrMedium : String = "m/s2";
        attribute semanticDefinition : String = "当前运行条件下允许的列车减速度上限。";
        attribute aliases : String = "最大减速度";
        attribute priority : String = "条件";
        attribute validityRule : String = "必须非负且在工程允许范围内;来源失效时能力应保守降级";
        attribute faultStrategy : String = "DegradeAvailability";
    }
    item def I_ITM_MEA_001 {
        attribute itemCode : String = "ITM-MEA-001";
        attribute chineseName : String = "列车速度";
        attribute englishName : String = "TrainSpeed";
        attribute family : String = "测量/反馈";
        attribute domain : String = "车辆运动";
        attribute datatype : String = "Real";
        attribute unitOrMedium : String = "m/s";
        attribute semanticDefinition : String = "用于制动力计算、混合控制、低速衰减和安全监控的列车纵向速度。";
        attribute aliases : String = "车速;运行速度";
        attribute priority : String = "核心";
        attribute validityRule : String = "范围+质量位+时间戳检查;单位必须固定";
        attribute faultStrategy : String = "RejectStale+QualityFlag";
    }
    item def I_ITM_MEA_002 {
        attribute itemCode : String = "ITM-MEA-002";
        attribute chineseName : String = "轴端角速度";
        attribute englishName : String = "AxleAngularSpeed";
        attribute family : String = "测量/反馈";
        attribute domain : String = "机械传动";
        attribute datatype : String = "Real";
        attribute unitOrMedium : String = "rad/s";
        attribute semanticDefinition : String = "轴端速度传感器测得的车轴角速度。";
        attribute aliases : String = "轮轴转速;轴速";
        attribute priority : String = "核心";
        attribute validityRule : String = "范围+质量位+时间戳检查;单位必须固定";
        attribute faultStrategy : String = "RejectStale+QualityFlag";
    }
    item def I_ITM_MEA_003 {
        attribute itemCode : String = "ITM-MEA-003";
        attribute chineseName : String = "齿轮箱转速";
        attribute englishName : String = "GearboxSpeed";
        attribute family : String = "测量/反馈";
        attribute domain : String = "机械传动";
        attribute datatype : String = "Real";
        attribute unitOrMedium : String = "rad/s";
        attribute semanticDefinition : String = "齿轮箱速度传感器测得的转速。";
        attribute aliases : String = "齿轮箱速度";
        attribute priority : String = "条件";
        attribute validityRule : String = "范围+质量位+时间戳检查;单位必须固定";
        attribute faultStrategy : String = "RejectStale+QualityFlag";
    }
    item def I_ITM_MEA_004 {
        attribute itemCode : String = "ITM-MEA-004";
        attribute chineseName : String = "牵引电机转速";
        attribute englishName : String = "MotorSpeed";
        attribute family : String = "测量/反馈";
        attribute domain : String = "牵引";
        attribute datatype : String = "Real";
        attribute unitOrMedium : String = "rad/s";
        attribute semanticDefinition : String = "牵引电机速度传感器或电机控制估算的电机机械角速度。";
        attribute aliases : String = "电机速度;omega_motor";
        attribute priority : String = "核心";
        attribute validityRule : String = "范围+质量位+时间戳检查;单位必须固定";
        attribute faultStrategy : String = "RejectStale+QualityFlag";
    }
    item def I_ITM_MEA_005 {
        attribute itemCode : String = "ITM-MEA-005";
        attribute chineseName : String = "高压线路电压";
        attribute englishName : String = "LineVoltage";
        attribute family : String = "测量/反馈";
        attribute domain : String = "主供电";
        attribute datatype : String = "Real";
        attribute unitOrMedium : String = "V";
        attribute semanticDefinition : String = "受流/高压测量通道得到的线路电压。";
        attribute aliases : String = "网压;接触网电压;线电压";
        attribute priority : String = "核心";
        attribute validityRule : String = "范围+质量位+时间戳检查;单位必须固定";
        attribute faultStrategy : String = "RejectStale+QualityFlag";
    }
    item def I_ITM_MEA_006 {
        attribute itemCode : String = "ITM-MEA-006";
        attribute chineseName : String = "高压线路电流";
        attribute englishName : String = "LineCurrent";
        attribute family : String = "测量/反馈";
        attribute domain : String = "主供电";
        attribute datatype : String = "Real";
        attribute unitOrMedium : String = "A";
        attribute semanticDefinition : String = "受流/高压测量通道得到的线路电流;符号用于区分取能与回馈。";
        attribute aliases : String = "网流;接触网电流";
        attribute priority : String = "核心";
        attribute validityRule : String = "范围+质量位+时间戳检查;单位必须固定";
        attribute faultStrategy : String = "RejectStale+QualityFlag";
    }
    item def I_ITM_MEA_007 {
        attribute itemCode : String = "ITM-MEA-007";
        attribute chineseName : String = "线路频率";
        attribute englishName : String = "LineFrequency";
        attribute family : String = "测量/反馈";
        attribute domain : String = "主供电";
        attribute datatype : String = "Real";
        attribute unitOrMedium : String = "Hz";
        attribute semanticDefinition : String = "交流供电方案的线路频率。";
        attribute aliases : String = "网频";
        attribute priority : String = "条件";
        attribute validityRule : String = "范围+质量位+时间戳检查;单位必须固定";
        attribute faultStrategy : String = "RejectStale+QualityFlag";
    }
    item def I_ITM_MEA_008 {
        attribute itemCode : String = "ITM-MEA-008";
        attribute chineseName : String = "中间直流母线电压";
        attribute englishName : String = "DCLinkVoltage";
        attribute family : String = "测量/反馈";
        attribute domain : String = "牵引/储能";
        attribute datatype : String = "Real";
        attribute unitOrMedium : String = "V";
        attribute semanticDefinition : String = "牵引变流器中间直流环节的电压。";
        attribute aliases : String = "Udc;DC-link voltage;母线电压";
        attribute priority : String = "核心";
        attribute validityRule : String = "范围+质量位+时间戳检查;单位必须固定";
        attribute faultStrategy : String = "RejectStale+QualityFlag";
    }
    item def I_ITM_MEA_009 {
        attribute itemCode : String = "ITM-MEA-009";
        attribute chineseName : String = "中间直流母线电流";
        attribute englishName : String = "DCLinkCurrent";
        attribute family : String = "测量/反馈";
        attribute domain : String = "牵引/储能";
        attribute datatype : String = "Real";
        attribute unitOrMedium : String = "A";
        attribute semanticDefinition : String = "中间直流环节电流或等效净电流。";
        attribute aliases : String = "Idc;母线电流";
        attribute priority : String = "核心";
        attribute validityRule : String = "范围+质量位+时间戳检查;单位必须固定";
        attribute faultStrategy : String = "RejectStale+QualityFlag";
    }
    item def I_ITM_MEA_010 {
        attribute itemCode : String = "ITM-MEA-010";
        attribute chineseName : String = "电机侧相电流";
        attribute englishName : String = "MotorPhaseCurrent";
        attribute family : String = "测量/反馈";
        attribute domain : String = "牵引";
        attribute datatype : String = "Real/Vector";
        attribute unitOrMedium : String = "A";
        attribute semanticDefinition : String = "电机侧变流器/牵引电机的三相电流测量。";
        attribute aliases : String = "Iabc;电机电流";
        attribute priority : String = "核心";
        attribute validityRule : String = "范围+质量位+时间戳检查;单位必须固定";
        attribute faultStrategy : String = "RejectStale+QualityFlag";
    }
    item def I_ITM_MEA_011 {
        attribute itemCode : String = "ITM-MEA-011";
        attribute chineseName : String = "电机侧相电压";
        attribute englishName : String = "MotorPhaseVoltage";
        attribute family : String = "测量/反馈";
        attribute domain : String = "牵引";
        attribute datatype : String = "Real/Vector";
        attribute unitOrMedium : String = "V";
        attribute semanticDefinition : String = "电机侧变流器/牵引电机的三相电压测量。";
        attribute aliases : String = "Vabc;电机电压";
        attribute priority : String = "条件";
        attribute validityRule : String = "范围+质量位+时间戳检查;单位必须固定";
        attribute faultStrategy : String = "RejectStale+QualityFlag";
    }
    item def I_ITM_MEA_012 {
        attribute itemCode : String = "ITM-MEA-012";
        attribute chineseName : String = "牵引电机实际转矩";
        attribute englishName : String = "MotorTorqueActual";
        attribute family : String = "测量/反馈";
        attribute domain : String = "牵引";
        attribute datatype : String = "Real";
        attribute unitOrMedium : String = "N·m";
        attribute semanticDefinition : String = "电机控制估算或测量的实际电磁转矩。";
        attribute aliases : String = "Te;实际电机转矩";
        attribute priority : String = "核心";
        attribute validityRule : String = "范围+质量位+时间戳检查;单位必须固定";
        attribute faultStrategy : String = "RejectStale+QualityFlag";
    }
    item def I_ITM_MEA_013 {
        attribute itemCode : String = "ITM-MEA-013";
        attribute chineseName : String = "实际动态制动力";
        attribute englishName : String = "AchievedDynamicBrakeForce";
        attribute family : String = "测量/反馈";
        attribute domain : String = "牵引/制动";
        attribute datatype : String = "Real";
        attribute unitOrMedium : String = "N";
        attribute semanticDefinition : String = "牵引电制动通道实际实现的列车等效动态制动力。";
        attribute aliases : String = "实际电制动力;动态制动力反馈";
        attribute priority : String = "核心";
        attribute validityRule : String = "范围+质量位+时间戳检查;单位必须固定";
        attribute faultStrategy : String = "RejectStale+QualityFlag";
    }
    item def I_ITM_MEA_014 {
        attribute itemCode : String = "ITM-MEA-014";
        attribute chineseName : String = "总风管压力";
        attribute englishName : String = "MainReservoirPressure";
        attribute family : String = "测量/反馈";
        attribute domain : String = "气动制动";
        attribute datatype : String = "Real";
        attribute unitOrMedium : String = "Pa";
        attribute semanticDefinition : String = "总风管压力传感器输出。";
        attribute aliases : String = "总风压力;MR pressure";
        attribute priority : String = "核心";
        attribute validityRule : String = "范围+质量位+时间戳检查;单位必须固定";
        attribute faultStrategy : String = "RejectStale+QualityFlag";
    }
    item def I_ITM_MEA_015 {
        attribute itemCode : String = "ITM-MEA-015";
        attribute chineseName : String = "制动风缸压力";
        attribute englishName : String = "BrakeReservoirPressure";
        attribute family : String = "测量/反馈";
        attribute domain : String = "气动制动";
        attribute datatype : String = "Real";
        attribute unitOrMedium : String = "Pa";
        attribute semanticDefinition : String = "制动风缸或局部储风容器压力。";
        attribute aliases : String = "储风缸压力;制动储气压力";
        attribute priority : String = "条件";
        attribute validityRule : String = "范围+质量位+时间戳检查;单位必须固定";
        attribute faultStrategy : String = "RejectStale+QualityFlag";
    }
    item def I_ITM_MEA_016 {
        attribute itemCode : String = "ITM-MEA-016";
        attribute chineseName : String = "制动缸压力";
        attribute englishName : String = "BrakeCylinderPressure";
        attribute family : String = "测量/反馈";
        attribute domain : String = "气动制动";
        attribute datatype : String = "Real";
        attribute unitOrMedium : String = "Pa";
        attribute semanticDefinition : String = "摩擦制动执行通道的制动缸/夹钳驱动压力。";
        attribute aliases : String = "BC pressure;制动压力";
        attribute priority : String = "核心";
        attribute validityRule : String = "范围+质量位+时间戳检查;单位必须固定";
        attribute faultStrategy : String = "RejectStale+QualityFlag";
    }
    item def I_ITM_MEA_017 {
        attribute itemCode : String = "ITM-MEA-017";
        attribute chineseName : String = "实际摩擦制动力";
        attribute englishName : String = "FrictionBrakeForceActual";
        attribute family : String = "测量/反馈";
        attribute domain : String = "制动";
        attribute datatype : String = "Real";
        attribute unitOrMedium : String = "N";
        attribute semanticDefinition : String = "由制动缸压力、执行机构特性或估算得到的实际摩擦制动力。";
        attribute aliases : String = "机械制动力反馈;空气制动力";
        attribute priority : String = "核心";
        attribute validityRule : String = "范围+质量位+时间戳检查;单位必须固定";
        attribute faultStrategy : String = "RejectStale+QualityFlag";
    }
    item def I_ITM_MEA_018 {
        attribute itemCode : String = "ITM-MEA-018";
        attribute chineseName : String = "列车质量";
        attribute englishName : String = "TrainMass";
        attribute family : String = "测量/反馈";
        attribute domain : String = "车辆状态";
        attribute datatype : String = "Real";
        attribute unitOrMedium : String = "kg";
        attribute semanticDefinition : String = "制动力计算使用的列车质量/等效质量信息。";
        attribute aliases : String = "列车载荷;质量";
        attribute priority : String = "条件";
        attribute validityRule : String = "范围+质量位+时间戳检查;单位必须固定";
        attribute faultStrategy : String = "RejectStale+QualityFlag";
    }
    item def I_ITM_MEA_019 {
        attribute itemCode : String = "ITM-MEA-019";
        attribute chineseName : String = "车辆载荷系数";
        attribute englishName : String = "VehicleLoadFactor";
        attribute family : String = "测量/反馈";
        attribute domain : String = "制动";
        attribute datatype : String = "Real";
        attribute unitOrMedium : String = "1";
        attribute semanticDefinition : String = "空重车调整或上层控制使用的车辆载荷归一化信息。";
        attribute aliases : String = "空重车系数;载荷率";
        attribute priority : String = "条件";
        attribute validityRule : String = "范围+质量位+时间戳检查;单位必须固定";
        attribute faultStrategy : String = "RejectStale+QualityFlag";
    }
    item def I_ITM_MEA_020 {
        attribute itemCode : String = "ITM-MEA-020";
        attribute chineseName : String = "轮轨滑移率";
        attribute englishName : String = "WheelSlipRatio";
        attribute family : String = "测量/反馈";
        attribute domain : String = "低黏着";
        attribute datatype : String = "Real";
        attribute unitOrMedium : String = "1";
        attribute semanticDefinition : String = "由轮速/车速估算的轮轨纵向滑移率。";
        attribute aliases : String = "滑行率;滑移率";
        attribute priority : String = "核心";
        attribute validityRule : String = "范围+质量位+时间戳检查;单位必须固定";
        attribute faultStrategy : String = "RejectStale+QualityFlag";
    }
    item def I_ITM_MEA_021 {
        attribute itemCode : String = "ITM-MEA-021";
        attribute chineseName : String = "可用黏着系数估计";
        attribute englishName : String = "AvailableAdhesionEstimate";
        attribute family : String = "测量/反馈";
        attribute domain : String = "低黏着";
        attribute datatype : String = "Real";
        attribute unitOrMedium : String = "1";
        attribute semanticDefinition : String = "控制器用于限制轮轨可传递纵向力的黏着能力估计。";
        attribute aliases : String = "mu;黏着系数";
        attribute priority : String = "条件";
        attribute validityRule : String = "范围+质量位+时间戳检查;单位必须固定";
        attribute faultStrategy : String = "RejectStale+QualityFlag";
    }
    item def I_ITM_MEA_022 {
        attribute itemCode : String = "ITM-MEA-022";
        attribute chineseName : String = "主变压器温度";
        attribute englishName : String = "MainTransformerTemperature";
        attribute family : String = "测量/反馈";
        attribute domain : String = "主供电";
        attribute datatype : String = "Real";
        attribute unitOrMedium : String = "°C";
        attribute semanticDefinition : String = "主变压器检测保护通道输出的代表性温度。";
        attribute aliases : String = "变压器温度";
        attribute priority : String = "条件";
        attribute validityRule : String = "范围+质量位+时间戳检查;单位必须固定";
        attribute faultStrategy : String = "RejectStale+QualityFlag";
    }
    item def I_ITM_MEA_023 {
        attribute itemCode : String = "ITM-MEA-023";
        attribute chineseName : String = "牵引变流器温度";
        attribute englishName : String = "TractionConverterTemperature";
        attribute family : String = "测量/反馈";
        attribute domain : String = "牵引";
        attribute datatype : String = "Real";
        attribute unitOrMedium : String = "°C";
        attribute semanticDefinition : String = "牵引变流器检测保护组件提供的代表性温度/热状态测量。";
        attribute aliases : String = "变流器温度;功率模块温度";
        attribute priority : String = "条件";
        attribute validityRule : String = "范围+质量位+时间戳检查;单位必须固定";
        attribute faultStrategy : String = "RejectStale+QualityFlag";
    }
    item def I_ITM_MEA_024 {
        attribute itemCode : String = "ITM-MEA-024";
        attribute chineseName : String = "制动电阻温度";
        attribute englishName : String = "BrakeResistorTemperature";
        attribute family : String = "测量/反馈";
        attribute domain : String = "牵引/能量";
        attribute datatype : String = "Real";
        attribute unitOrMedium : String = "°C";
        attribute semanticDefinition : String = "制动电阻/斩波耗散支路的代表性温度。";
        attribute aliases : String = "电阻温度;斩波电阻温度";
        attribute priority : String = "条件";
        attribute validityRule : String = "范围+质量位+时间戳检查;单位必须固定";
        attribute faultStrategy : String = "RejectStale+QualityFlag";
    }
    item def I_ITM_MEA_025 {
        attribute itemCode : String = "ITM-MEA-025";
        attribute chineseName : String = "超级电容电压";
        attribute englishName : String = "SuperCapVoltage";
        attribute family : String = "测量/反馈";
        attribute domain : String = "储能";
        attribute datatype : String = "Real";
        attribute unitOrMedium : String = "V";
        attribute semanticDefinition : String = "超级电容模块端电压。";
        attribute aliases : String = "Usc;SC voltage";
        attribute priority : String = "核心";
        attribute validityRule : String = "范围+质量位+时间戳检查;单位必须固定";
        attribute faultStrategy : String = "RejectStale+QualityFlag";
    }
    item def I_ITM_MEA_026 {
        attribute itemCode : String = "ITM-MEA-026";
        attribute chineseName : String = "超级电容电流";
        attribute englishName : String = "SuperCapCurrent";
        attribute family : String = "测量/反馈";
        attribute domain : String = "储能";
        attribute datatype : String = "Real";
        attribute unitOrMedium : String = "A";
        attribute semanticDefinition : String = "超级电容支路电流;正负号方向必须项目内固定。";
        attribute aliases : String = "Isc;SC current";
        attribute priority : String = "核心";
        attribute validityRule : String = "范围+质量位+时间戳检查;单位必须固定";
        attribute faultStrategy : String = "RejectStale+QualityFlag";
    }
    item def I_ITM_MEA_027 {
        attribute itemCode : String = "ITM-MEA-027";
        attribute chineseName : String = "超级电容温度";
        attribute englishName : String = "SuperCapTemperature";
        attribute family : String = "测量/反馈";
        attribute domain : String = "储能";
        attribute datatype : String = "Real";
        attribute unitOrMedium : String = "°C";
        attribute semanticDefinition : String = "超级电容模块代表性温度。";
        attribute aliases : String = "Tsc;SC temperature";
        attribute priority : String = "核心";
        attribute validityRule : String = "范围+质量位+时间戳检查;单位必须固定";
        attribute faultStrategy : String = "RejectStale+QualityFlag";
    }
    item def I_ITM_MEA_028 {
        attribute itemCode : String = "ITM-MEA-028";
        attribute chineseName : String = "超级电容SOC";
        attribute englishName : String = "SuperCapSOC";
        attribute family : String = "测量/反馈";
        attribute domain : String = "储能";
        attribute datatype : String = "Real";
        attribute unitOrMedium : String = "1";
        attribute semanticDefinition : String = "由超级电容电压/能量模型估算的归一化储能状态。";
        attribute aliases : String = "SOC;SC SOC";
        attribute priority : String = "核心";
        attribute validityRule : String = "范围+质量位+时间戳检查;单位必须固定";
        attribute faultStrategy : String = "RejectStale+QualityFlag";
    }
    item def I_ITM_MEA_029 {
        attribute itemCode : String = "ITM-MEA-029";
        attribute chineseName : String = "双向DC/DC实际功率";
        attribute englishName : String = "DCDCActualPower";
        attribute family : String = "测量/反馈";
        attribute domain : String = "储能";
        attribute datatype : String = "Real";
        attribute unitOrMedium : String = "W";
        attribute semanticDefinition : String = "双向DC/DC实际向储能侧或母线侧传递的功率。";
        attribute aliases : String = "P_ESS_actual;DC/DC功率";
        attribute priority : String = "核心";
        attribute validityRule : String = "范围+质量位+时间戳检查;单位必须固定";
        attribute faultStrategy : String = "RejectStale+QualityFlag";
    }
    item def I_ITM_MEA_030 {
        attribute itemCode : String = "ITM-MEA-030";
        attribute chineseName : String = "双向DC/DC电流";
        attribute englishName : String = "DCDCCurrent";
        attribute family : String = "测量/反馈";
        attribute domain : String = "储能";
        attribute datatype : String = "Real";
        attribute unitOrMedium : String = "A";
        attribute semanticDefinition : String = "双向DC/DC关键支路电流测量。";
        attribute aliases : String = "DC/DC电流";
        attribute priority : String = "条件";
        attribute validityRule : String = "范围+质量位+时间戳检查;单位必须固定";
        attribute faultStrategy : String = "RejectStale+QualityFlag";
    }
    item def I_ITM_MEA_031 {
        attribute itemCode : String = "ITM-MEA-031";
        attribute chineseName : String = "列车加速度/减速度";
        attribute englishName : String = "TrainAcceleration";
        attribute family : String = "测量/反馈";
        attribute domain : String = "车辆运动";
        attribute datatype : String = "Real";
        attribute unitOrMedium : String = "m/s2";
        attribute semanticDefinition : String = "用于性能验证和制动闭环监测的纵向加速度,制动时通常为负或按项目约定采用正减速度。";
        attribute aliases : String = "列车减速度;纵向加速度";
        attribute priority : String = "条件";
        attribute validityRule : String = "范围+质量位+时间戳检查;单位必须固定";
        attribute faultStrategy : String = "RejectStale+QualityFlag";
    }
    item def I_ITM_PHY_001 {
        attribute itemCode : String = "ITM-PHY-001";
        attribute chineseName : String = "高压交流电能";
        attribute englishName : String = "HighVoltageACElectricalEnergy";
        attribute family : String = "物理交换";
        attribute domain : String = "主供电";
        attribute datatype : String = "PhysicalConnector";
        attribute unitOrMedium : String = "高压交流电气";
        attribute semanticDefinition : String = "受电弓/高压回路/主变压器/网侧变流器之间传递的高压交流电能;电压、电流、频率为该物理域的伴随变量。";
        attribute aliases : String = "接触网电能;25kV交流电能;网侧交流电能";
        attribute priority : String = "条件";
        attribute validityRule : String = "物理网络守恒;供电制式必须一致";
        attribute faultStrategy : String = "PhysicalConservation";
    }
    item def I_ITM_PHY_002 {
        attribute itemCode : String = "ITM-PHY-002";
        attribute chineseName : String = "直流牵引供电电能";
        attribute englishName : String = "TractionDCElectricalEnergy";
        attribute family : String = "物理交换";
        attribute domain : String = "主供电";
        attribute datatype : String = "PhysicalConnector";
        attribute unitOrMedium : String = "直流电气";
        attribute semanticDefinition : String = "直流受流方案中受流器与牵引主回路之间传递的直流电能。";
        attribute aliases : String = "接触轨电能;直流网电能;1500V直流电能";
        attribute priority : String = "条件";
        attribute validityRule : String = "物理网络守恒;极性/电压等级一致";
        attribute faultStrategy : String = "PhysicalConservation";
    }
    item def I_ITM_PHY_003 {
        attribute itemCode : String = "ITM-PHY-003";
        attribute chineseName : String = "中间直流电能";
        attribute englishName : String = "DCLinkElectricalEnergy";
        attribute family : String = "物理交换";
        attribute domain : String = "牵引/储能";
        attribute datatype : String = "PhysicalConnector";
        attribute unitOrMedium : String = "直流电气";
        attribute semanticDefinition : String = "牵引变流器中间直流环节、制动电阻支路和储能支路之间传递的直流电能。";
        attribute aliases : String = "DC-link电能;直流母线电能;中间电路电能";
        attribute priority : String = "核心";
        attribute validityRule : String = "物理网络守恒;电压等级兼容";
        attribute faultStrategy : String = "PhysicalConservation";
    }
    item def I_ITM_PHY_004 {
        attribute itemCode : String = "ITM-PHY-004";
        attribute chineseName : String = "三相交流电能";
        attribute englishName : String = "ThreePhaseACElectricalEnergy";
        attribute family : String = "物理交换";
        attribute domain : String = "牵引";
        attribute datatype : String = "PhysicalConnector";
        attribute unitOrMedium : String = "三相交流电气";
        attribute semanticDefinition : String = "电机侧变流模块与牵引电机之间双向传递的三相交流电能。";
        attribute aliases : String = "电机三相电能;逆变器输出电能";
        attribute priority : String = "核心";
        attribute validityRule : String = "物理网络守恒;相制/频率/电压兼容";
        attribute faultStrategy : String = "PhysicalConservation";
    }
    item def I_ITM_PHY_005 {
        attribute itemCode : String = "ITM-PHY-005";
        attribute chineseName : String = "旋转机械能";
        attribute englishName : String = "RotationalMechanicalEnergy";
        attribute family : String = "物理交换";
        attribute domain : String = "机械传动";
        attribute datatype : String = "PhysicalConnector";
        attribute unitOrMedium : String = "旋转机械";
        attribute semanticDefinition : String = "牵引电机、联轴节、万向轴、齿轮箱、车轴和车轮之间双向传递的旋转机械能;伴随变量为转矩与角速度。";
        attribute aliases : String = "轴系机械能;旋转功率;机械轴功率";
        attribute priority : String = "核心";
        attribute validityRule : String = "机械网络守恒;轴系方向/转速基准一致";
        attribute faultStrategy : String = "PhysicalConservation";
    }
    item def I_ITM_PHY_006 {
        attribute itemCode : String = "ITM-PHY-006";
        attribute chineseName : String = "轮轨纵向机械作用";
        attribute englishName : String = "WheelRailLongitudinalInteraction";
        attribute family : String = "物理交换";
        attribute domain : String = "轮轨";
        attribute datatype : String = "PhysicalConnector";
        attribute unitOrMedium : String = "纵向机械";
        attribute semanticDefinition : String = "车轮与轨道之间的纵向牵引/制动力机械作用,用于把轮轴转矩映射为车辆纵向力。";
        attribute aliases : String = "轮轨牵引力;轮轨制动力;黏着力";
        attribute priority : String = "核心";
        attribute validityRule : String = "力方向与车辆坐标系一致";
        attribute faultStrategy : String = "PhysicalConservation";
    }
    item def I_ITM_PHY_007 {
        attribute itemCode : String = "ITM-PHY-007";
        attribute chineseName : String = "摩擦制动机械作用";
        attribute englishName : String = "FrictionBrakeMechanicalInteraction";
        attribute family : String = "物理交换";
        attribute domain : String = "摩擦制动";
        attribute datatype : String = "PhysicalConnector";
        attribute unitOrMedium : String = "摩擦机械";
        attribute semanticDefinition : String = "制动夹钳、闸片和制动盘之间的机械夹紧与摩擦作用,形成制动力矩并耗散机械能。";
        attribute aliases : String = "夹紧力;摩擦力;制动力矩作用";
        attribute priority : String = "核心";
        attribute validityRule : String = "机械作用方向一致;仅在接触有效时成立";
        attribute faultStrategy : String = "PhysicalConservation";
    }
    item def I_ITM_PHY_008 {
        attribute itemCode : String = "ITM-PHY-008";
        attribute chineseName : String = "主风压缩空气";
        attribute englishName : String = "MainReservoirCompressedAir";
        attribute family : String = "物理交换";
        attribute domain : String = "气动制动";
        attribute datatype : String = "PhysicalConnector";
        attribute unitOrMedium : String = "压缩空气";
        attribute semanticDefinition : String = "总风管/风缸向制动气路提供的压缩空气介质。";
        attribute aliases : String = "总风;主风;供风";
        attribute priority : String = "核心";
        attribute validityRule : String = "压力/流量方向符合气动网络";
        attribute faultStrategy : String = "PhysicalConservation";
    }
    item def I_ITM_PHY_009 {
        attribute itemCode : String = "ITM-PHY-009";
        attribute chineseName : String = "制动控制压缩空气";
        attribute englishName : String = "BrakeControlCompressedAir";
        attribute family : String = "物理交换";
        attribute domain : String = "气动制动";
        attribute datatype : String = "PhysicalConnector";
        attribute unitOrMedium : String = "压缩空气";
        attribute semanticDefinition : String = "电空转换阀、调压阀、中继阀、防滑阀等制动控制元件之间传递的受控压缩空气。";
        attribute aliases : String = "先导气;控制风;制动控制气路";
        attribute priority : String = "核心";
        attribute validityRule : String = "压力范围有效;气路连通";
        attribute faultStrategy : String = "PhysicalConservation";
    }
    item def I_ITM_PHY_010 {
        attribute itemCode : String = "ITM-PHY-010";
        attribute chineseName : String = "制动缸压缩空气";
        attribute englishName : String = "BrakeCylinderCompressedAir";
        attribute family : String = "物理交换";
        attribute domain : String = "气动制动";
        attribute datatype : String = "PhysicalConnector";
        attribute unitOrMedium : String = "压缩空气";
        attribute semanticDefinition : String = "中继阀/增压缸/制动夹钳执行机构之间用于产生摩擦制动力的压缩空气。";
        attribute aliases : String = "制动缸空气;制动缸气路";
        attribute priority : String = "核心";
        attribute validityRule : String = "压力范围有效;泄漏/隔离状态可判定";
        attribute faultStrategy : String = "PhysicalConservation";
    }
    item def I_ITM_PHY_011 {
        attribute itemCode : String = "ITM-PHY-011";
        attribute chineseName : String = "主回路回流电流";
        attribute englishName : String = "TractionReturnCurrent";
        attribute family : String = "物理交换";
        attribute domain : String = "主供电";
        attribute datatype : String = "PhysicalConnector";
        attribute unitOrMedium : String = "电气回流";
        attribute semanticDefinition : String = "牵引/再生主回路经车体接地、回流碳刷等返回供电系统的电流路径。";
        attribute aliases : String = "回流电流;牵引回流;接地回流";
        attribute priority : String = "核心";
        attribute validityRule : String = "回流路径连续;绝缘/接地边界一致";
        attribute faultStrategy : String = "PhysicalConservation";
    }
    item def I_ITM_PHY_012 {
        attribute itemCode : String = "ITM-PHY-012";
        attribute chineseName : String = "砂流";
        attribute englishName : String = "SandFlow";
        attribute family : String = "物理交换";
        attribute domain : String = "低黏着管理";
        attribute datatype : String = "PhysicalConnector";
        attribute unitOrMedium : String = "散粒介质";
        attribute semanticDefinition : String = "撒砂阀板至撒砂喷嘴并最终作用于轮轨界面的砂粒介质流。";
        attribute aliases : String = "撒砂介质;砂粒流";
        attribute priority : String = "条件";
        attribute validityRule : String = "仅在撒砂命令有效且设备可用时传递";
        attribute faultStrategy : String = "PhysicalConservation";
    }
    item def I_ITM_PHY_013 {
        attribute itemCode : String = "ITM-PHY-013";
        attribute chineseName : String = "热能/热流";
        attribute englishName : String = "ThermalEnergyFlow";
        attribute family : String = "物理交换";
        attribute domain : String = "热耗散";
        attribute datatype : String = "PhysicalConnector";
        attribute unitOrMedium : String = "热";
        attribute semanticDefinition : String = "制动电阻、摩擦制动和储能组件向环境或热管理系统释放的热能。";
        attribute aliases : String = "热流;耗散热能";
        attribute priority : String = "条件";
        attribute validityRule : String = "热功率非负;热边界定义一致";
        attribute faultStrategy : String = "PhysicalConservation";
    }
    item def I_ITM_PHY_014 {
        attribute itemCode : String = "ITM-PHY-014";
        attribute chineseName : String = "牵引变压器次级交流电能";
        attribute englishName : String = "TractionTransformerSecondaryACEnergy";
        attribute family : String = "物理交换";
        attribute domain : String = "主供电/牵引";
        attribute datatype : String = "PhysicalConnector";
        attribute unitOrMedium : String = "交流电气";
        attribute semanticDefinition : String = "主变压器次级绕组、电抗器、输入单元与网侧变流模块之间传递的牵引交流电能。";
        attribute aliases : String = "变压器次级电能;牵引次级交流;网侧变流器输入交流";
        attribute priority : String = "条件";
        attribute validityRule : String = "物理网络守恒;绕组/电压等级兼容";
        attribute faultStrategy : String = "PhysicalConservation";
    }
    item def I_ITM_PHY_015 {
        attribute itemCode : String = "ITM-PHY-015";
        attribute chineseName : String = "低压控制电能";
        attribute englishName : String = "LowVoltageControlPower";
        attribute family : String = "物理交换";
        attribute domain : String = "控制供电";
        attribute datatype : String = "PhysicalConnector";
        attribute unitOrMedium : String = "低压直流电气";
        attribute semanticDefinition : String = "EBCU、VCU、控制单元、I/O、安全回路、接触器线圈及保护电子设备使用的低压控制电源。";
        attribute aliases : String = "控制电源;110VDC;24VDC;低压直流电源";
        attribute priority : String = "条件";
        attribute validityRule : String = "电压等级/极性兼容;供电可用性可监测";
        attribute faultStrategy : String = "PhysicalConservation";
    }
    item def I_ITM_PHY_016 {
        attribute itemCode : String = "ITM-PHY-016";
        attribute chineseName : String = "储能侧直流电能";
        attribute englishName : String = "ESSSideDCElectricalEnergy";
        attribute family : String = "物理交换";
        attribute domain : String = "储能";
        attribute datatype : String = "PhysicalConnector";
        attribute unitOrMedium : String = "直流电气";
        attribute semanticDefinition : String = "双向DC/DC储能侧与超级电容模块之间传递的直流电能。";
        attribute aliases : String = "超级电容侧直流电能;SC侧电能;低压储能直流";
        attribute priority : String = "核心";
        attribute validityRule : String = "物理网络守恒;电压等级兼容";
        attribute faultStrategy : String = "PhysicalConservation";
    }
    item def I_ITM_STA_001 {
        attribute itemCode : String = "ITM-STA-001";
        attribute chineseName : String = "牵引可用状态";
        attribute englishName : String = "TractionAvailability";
        attribute family : String = "状态/故障";
        attribute domain : String = "牵引";
        attribute datatype : String = "Boolean";
        attribute unitOrMedium : String = "无";
        attribute semanticDefinition : String = "牵引系统是否具备正常输出牵引/动态制动能力。";
        attribute aliases : String = "牵引可用;traction available";
        attribute priority : String = "核心";
        attribute validityRule : String = "枚举/位集值域固定;需有效位和时间戳";
        attribute faultStrategy : String = "DegradeAvailability";
    }
    item def I_ITM_STA_002 {
        attribute itemCode : String = "ITM-STA-002";
        attribute chineseName : String = "动态制动可用状态";
        attribute englishName : String = "DynamicBrakeAvailability";
        attribute family : String = "状态/故障";
        attribute domain : String = "牵引/制动";
        attribute datatype : String = "Boolean";
        attribute unitOrMedium : String = "无";
        attribute semanticDefinition : String = "动态制动通道是否可用于当前制动力分配。";
        attribute aliases : String = "电制动可用;再生制动可用";
        attribute priority : String = "核心";
        attribute validityRule : String = "枚举/位集值域固定;需有效位和时间戳";
        attribute faultStrategy : String = "DegradeAvailability";
    }
    item def I_ITM_STA_003 {
        attribute itemCode : String = "ITM-STA-003";
        attribute chineseName : String = "制动系统可用状态";
        attribute englishName : String = "BrakeAvailability";
        attribute family : String = "状态/故障";
        attribute domain : String = "制动";
        attribute datatype : String = "Boolean";
        attribute unitOrMedium : String = "无";
        attribute semanticDefinition : String = "制动控制/执行系统是否具备请求的制动能力。";
        attribute aliases : String = "制动可用";
        attribute priority : String = "核心";
        attribute validityRule : String = "枚举/位集值域固定;需有效位和时间戳";
        attribute faultStrategy : String = "DegradeAvailability";
    }
    item def I_ITM_STA_004 {
        attribute itemCode : String = "ITM-STA-004";
        attribute chineseName : String = "制动施加状态";
        attribute englishName : String = "BrakeAppliedState";
        attribute family : String = "状态/故障";
        attribute domain : String = "制动";
        attribute datatype : String = "Boolean";
        attribute unitOrMedium : String = "无";
        attribute semanticDefinition : String = "相关制动通道当前是否处于施加状态。";
        attribute aliases : String = "制动已施加";
        attribute priority : String = "核心";
        attribute validityRule : String = "枚举/位集值域固定;需有效位和时间戳";
        attribute faultStrategy : String = "QualityFlag";
    }
    item def I_ITM_STA_005 {
        attribute itemCode : String = "ITM-STA-005";
        attribute chineseName : String = "制动缓解状态";
        attribute englishName : String = "BrakeReleasedState";
        attribute family : String = "状态/故障";
        attribute domain : String = "制动";
        attribute datatype : String = "Boolean";
        attribute unitOrMedium : String = "无";
        attribute semanticDefinition : String = "相关制动通道当前是否处于缓解状态。";
        attribute aliases : String = "制动释放状态";
        attribute priority : String = "核心";
        attribute validityRule : String = "枚举/位集值域固定;需有效位和时间戳";
        attribute faultStrategy : String = "QualityFlag";
    }
    item def I_ITM_STA_006 {
        attribute itemCode : String = "ITM-STA-006";
        attribute chineseName : String = "制动隔离状态";
        attribute englishName : String = "BrakeIsolationState";
        attribute family : String = "状态/故障";
        attribute domain : String = "制动";
        attribute datatype : String = "Boolean";
        attribute unitOrMedium : String = "无";
        attribute semanticDefinition : String = "相关制动通道是否被永久/局部隔离。";
        attribute aliases : String = "制动截断状态;隔离状态";
        attribute priority : String = "核心";
        attribute validityRule : String = "枚举/位集值域固定;需有效位和时间戳";
        attribute faultStrategy : String = "DegradeAvailability";
    }
    item def I_ITM_STA_007 {
        attribute itemCode : String = "ITM-STA-007";
        attribute chineseName : String = "制动控制故障状态";
        attribute englishName : String = "BrakeControlFault";
        attribute family : String = "状态/故障";
        attribute domain : String = "制动";
        attribute datatype : String = "Enum/Bitset";
        attribute unitOrMedium : String = "无";
        attribute semanticDefinition : String = "EBCU或制动控制链故障状态。";
        attribute aliases : String = "EBCU故障;制动故障";
        attribute priority : String = "核心";
        attribute validityRule : String = "枚举/位集值域固定;需有效位和时间戳";
        attribute faultStrategy : String = "SafeFallback";
    }
    item def I_ITM_STA_008 {
        attribute itemCode : String = "ITM-STA-008";
        attribute chineseName : String = "制动拖滞状态";
        attribute englishName : String = "DraggingBrakeState";
        attribute family : String = "状态/故障";
        attribute domain : String = "制动";
        attribute datatype : String = "Boolean";
        attribute unitOrMedium : String = "无";
        attribute semanticDefinition : String = "无有效制动请求但检测到非零制动力的拖滞状态。";
        attribute aliases : String = "拖闸;制动拖滞";
        attribute priority : String = "条件";
        attribute validityRule : String = "枚举/位集值域固定;需有效位和时间戳";
        attribute faultStrategy : String = "SafeFallback";
    }
    item def I_ITM_STA_009 {
        attribute itemCode : String = "ITM-STA-009";
        attribute chineseName : String = "低风压状态";
        attribute englishName : String = "LowPneumaticPressureState";
        attribute family : String = "状态/故障";
        attribute domain : String = "气动制动";
        attribute datatype : String = "Boolean";
        attribute unitOrMedium : String = "无";
        attribute semanticDefinition : String = "气动能源低于可用阈值的状态。";
        attribute aliases : String = "低气压;制动气源不足";
        attribute priority : String = "核心";
        attribute validityRule : String = "枚举/位集值域固定;需有效位和时间戳";
        attribute faultStrategy : String = "DegradeAvailability";
    }
    item def I_ITM_STA_010 {
        attribute itemCode : String = "ITM-STA-010";
        attribute chineseName : String = "防滑激活状态";
        attribute englishName : String = "WSPActiveState";
        attribute family : String = "状态/故障";
        attribute domain : String = "低黏着";
        attribute datatype : String = "Boolean";
        attribute unitOrMedium : String = "无";
        attribute semanticDefinition : String = "WSP当前是否正在干预制动力。";
        attribute aliases : String = "防滑动作;WSP active";
        attribute priority : String = "核心";
        attribute validityRule : String = "枚举/位集值域固定;需有效位和时间戳";
        attribute faultStrategy : String = "QualityFlag";
    }
    item def I_ITM_STA_011 {
        attribute itemCode : String = "ITM-STA-011";
        attribute chineseName : String = "防滑故障状态";
        attribute englishName : String = "WSPFaultState";
        attribute family : String = "状态/故障";
        attribute domain : String = "低黏着";
        attribute datatype : String = "Boolean";
        attribute unitOrMedium : String = "无";
        attribute semanticDefinition : String = "防滑控制/阀组故障状态。";
        attribute aliases : String = "WSP fault";
        attribute priority : String = "条件";
        attribute validityRule : String = "枚举/位集值域固定;需有效位和时间戳";
        attribute faultStrategy : String = "SafeFallback";
    }
    item def I_ITM_STA_012 {
        attribute itemCode : String = "ITM-STA-012";
        attribute chineseName : String = "撒砂状态";
        attribute englishName : String = "SandingState";
        attribute family : String = "状态/故障";
        attribute domain : String = "低黏着";
        attribute datatype : String = "Enum";
        attribute unitOrMedium : String = "无";
        attribute semanticDefinition : String = "撒砂系统空闲/执行/故障等状态。";
        attribute aliases : String = "撒砂执行状态";
        attribute priority : String = "条件";
        attribute validityRule : String = "枚举/位集值域固定;需有效位和时间戳";
        attribute faultStrategy : String = "QualityFlag";
    }
    item def I_ITM_STA_013 {
        attribute itemCode : String = "ITM-STA-013";
        attribute chineseName : String = "高压断路器状态";
        attribute englishName : String = "HVBreakerState";
        attribute family : String = "状态/故障";
        attribute domain : String = "主供电";
        attribute datatype : String = "Enum";
        attribute unitOrMedium : String = "无";
        attribute semanticDefinition : String = "高压断路器分/合/跳闸状态。";
        attribute aliases : String = "VCB状态;主断状态";
        attribute priority : String = "条件";
        attribute validityRule : String = "枚举/位集值域固定;需有效位和时间戳";
        attribute faultStrategy : String = "SafeFallback";
    }
    item def I_ITM_STA_014 {
        attribute itemCode : String = "ITM-STA-014";
        attribute chineseName : String = "高压隔离开关状态";
        attribute englishName : String = "HVIsolationSwitchState";
        attribute family : String = "状态/故障";
        attribute domain : String = "主供电";
        attribute datatype : String = "Enum";
        attribute unitOrMedium : String = "无";
        attribute semanticDefinition : String = "高压隔离开关状态。";
        attribute aliases : String = "隔离开关状态";
        attribute priority : String = "条件";
        attribute validityRule : String = "枚举/位集值域固定;需有效位和时间戳";
        attribute faultStrategy : String = "SafeFallback";
    }
    item def I_ITM_STA_015 {
        attribute itemCode : String = "ITM-STA-015";
        attribute chineseName : String = "受电弓状态";
        attribute englishName : String = "PantographState";
        attribute family : String = "状态/故障";
        attribute domain : String = "主供电";
        attribute datatype : String = "Enum";
        attribute unitOrMedium : String = "无";
        attribute semanticDefinition : String = "受电弓升/降/接触异常等状态。";
        attribute aliases : String = "升弓状态;受流状态";
        attribute priority : String = "条件";
        attribute validityRule : String = "枚举/位集值域固定;需有效位和时间戳";
        attribute faultStrategy : String = "SafeFallback";
    }
    item def I_ITM_STA_016 {
        attribute itemCode : String = "ITM-STA-016";
        attribute chineseName : String = "高压系统故障状态";
        attribute englishName : String = "HVSystemFault";
        attribute family : String = "状态/故障";
        attribute domain : String = "主供电";
        attribute datatype : String = "Enum/Bitset";
        attribute unitOrMedium : String = "无";
        attribute semanticDefinition : String = "高压测量、断路器、绝缘或主变压器等高压系统故障集合。";
        attribute aliases : String = "高压故障";
        attribute priority : String = "核心";
        attribute validityRule : String = "枚举/位集值域固定;需有效位和时间戳";
        attribute faultStrategy : String = "SafeFallback";
    }
    item def I_ITM_STA_017 {
        attribute itemCode : String = "ITM-STA-017";
        attribute chineseName : String = "网侧变流器状态";
        attribute englishName : String = "GridSideConverterState";
        attribute family : String = "状态/故障";
        attribute domain : String = "牵引";
        attribute datatype : String = "Enum";
        attribute unitOrMedium : String = "无";
        attribute semanticDefinition : String = "网侧变流器控制/功率模块运行状态。";
        attribute aliases : String = "网侧变流状态";
        attribute priority : String = "核心";
        attribute validityRule : String = "枚举/位集值域固定;需有效位和时间戳";
        attribute faultStrategy : String = "DegradeAvailability";
    }
    item def I_ITM_STA_018 {
        attribute itemCode : String = "ITM-STA-018";
        attribute chineseName : String = "电机侧变流器状态";
        attribute englishName : String = "MotorSideConverterState";
        attribute family : String = "状态/故障";
        attribute domain : String = "牵引";
        attribute datatype : String = "Enum";
        attribute unitOrMedium : String = "无";
        attribute semanticDefinition : String = "电机侧变流器运行状态。";
        attribute aliases : String = "逆变器状态;电机侧状态";
        attribute priority : String = "核心";
        attribute validityRule : String = "枚举/位集值域固定;需有效位和时间戳";
        attribute faultStrategy : String = "DegradeAvailability";
    }
    item def I_ITM_STA_019 {
        attribute itemCode : String = "ITM-STA-019";
        attribute chineseName : String = "牵引变流器故障状态";
        attribute englishName : String = "TractionConverterFault";
        attribute family : String = "状态/故障";
        attribute domain : String = "牵引";
        attribute datatype : String = "Enum/Bitset";
        attribute unitOrMedium : String = "无";
        attribute semanticDefinition : String = "牵引变流器保护/故障集合。";
        attribute aliases : String = "变流器故障";
        attribute priority : String = "核心";
        attribute validityRule : String = "枚举/位集值域固定;需有效位和时间戳";
        attribute faultStrategy : String = "SafeFallback";
    }
    item def I_ITM_STA_020 {
        attribute itemCode : String = "ITM-STA-020";
        attribute chineseName : String = "中间直流环节保护状态";
        attribute englishName : String = "DCLinkProtectionState";
        attribute family : String = "状态/故障";
        attribute domain : String = "牵引";
        attribute datatype : String = "Enum/Bitset";
        attribute unitOrMedium : String = "无";
        attribute semanticDefinition : String = "直流母线过压/欠压/过流等保护状态。";
        attribute aliases : String = "DC-link保护;母线保护";
        attribute priority : String = "核心";
        attribute validityRule : String = "枚举/位集值域固定;需有效位和时间戳";
        attribute faultStrategy : String = "SafeFallback";
    }
    item def I_ITM_STA_021 {
        attribute itemCode : String = "ITM-STA-021";
        attribute chineseName : String = "预充电状态";
        attribute englishName : String = "TractionPrechargeState";
        attribute family : String = "状态/故障";
        attribute domain : String = "牵引";
        attribute datatype : String = "Enum";
        attribute unitOrMedium : String = "无";
        attribute semanticDefinition : String = "牵引输入预充电过程状态。";
        attribute aliases : String = "预充完成;预充故障";
        attribute priority : String = "核心";
        attribute validityRule : String = "枚举/位集值域固定;需有效位和时间戳";
        attribute faultStrategy : String = "SafeFallback";
    }
    item def I_ITM_STA_022 {
        attribute itemCode : String = "ITM-STA-022";
        attribute chineseName : String = "牵引输入接通状态";
        attribute englishName : String = "TractionInputConnectionState";
        attribute family : String = "状态/故障";
        attribute domain : String = "牵引";
        attribute datatype : String = "Enum";
        attribute unitOrMedium : String = "无";
        attribute semanticDefinition : String = "牵引输入主回路接通/断开状态。";
        attribute aliases : String = "输入接触状态";
        attribute priority : String = "核心";
        attribute validityRule : String = "枚举/位集值域固定;需有效位和时间戳";
        attribute faultStrategy : String = "SafeFallback";
    }
    item def I_ITM_STA_023 {
        attribute itemCode : String = "ITM-STA-023";
        attribute chineseName : String = "制动斩波器状态";
        attribute englishName : String = "BrakeChopperState";
        attribute family : String = "状态/故障";
        attribute domain : String = "牵引/能量";
        attribute datatype : String = "Enum";
        attribute unitOrMedium : String = "无";
        attribute semanticDefinition : String = "制动斩波器可用/投入/故障状态。";
        attribute aliases : String = "放电电阻支路状态";
        attribute priority : String = "核心";
        attribute validityRule : String = "枚举/位集值域固定;需有效位和时间戳";
        attribute faultStrategy : String = "DegradeAvailability";
    }
    item def I_ITM_STA_024 {
        attribute itemCode : String = "ITM-STA-024";
        attribute chineseName : String = "高压安全回路状态";
        attribute englishName : String = "HVSafetyLoopState";
        attribute family : String = "状态/故障";
        attribute domain : String = "安全";
        attribute datatype : String = "Boolean/Enum";
        attribute unitOrMedium : String = "无";
        attribute semanticDefinition : String = "高压相关安全回路闭合/断开/故障状态。";
        attribute aliases : String = "高压安全链";
        attribute priority : String = "核心";
        attribute validityRule : String = "枚举/位集值域固定;需有效位和时间戳";
        attribute faultStrategy : String = "SafeFallback";
    }
    item def I_ITM_STA_025 {
        attribute itemCode : String = "ITM-STA-025";
        attribute chineseName : String = "制动安全回路状态";
        attribute englishName : String = "BrakeSafetyLoopState";
        attribute family : String = "状态/故障";
        attribute domain : String = "安全";
        attribute datatype : String = "Boolean/Enum";
        attribute unitOrMedium : String = "无";
        attribute semanticDefinition : String = "制动安全回路状态。";
        attribute aliases : String = "制动安全链";
        attribute priority : String = "核心";
        attribute validityRule : String = "枚举/位集值域固定;需有效位和时间戳";
        attribute faultStrategy : String = "SafeFallback";
    }
    item def I_ITM_STA_026 {
        attribute itemCode : String = "ITM-STA-026";
        attribute chineseName : String = "牵引安全回路状态";
        attribute englishName : String = "TractionSafetyLoopState";
        attribute family : String = "状态/故障";
        attribute domain : String = "安全";
        attribute datatype : String = "Boolean/Enum";
        attribute unitOrMedium : String = "无";
        attribute semanticDefinition : String = "牵引安全回路状态。";
        attribute aliases : String = "牵引安全链";
        attribute priority : String = "核心";
        attribute validityRule : String = "枚举/位集值域固定;需有效位和时间戳";
        attribute faultStrategy : String = "SafeFallback";
    }
    item def I_ITM_STA_027 {
        attribute itemCode : String = "ITM-STA-027";
        attribute chineseName : String = "ATP/外部安全系统状态";
        attribute englishName : String = "ExternalSafetySystemState";
        attribute family : String = "状态/故障";
        attribute domain : String = "安全";
        attribute datatype : String = "Enum/Bitset";
        attribute unitOrMedium : String = "无";
        attribute semanticDefinition : String = "ATP等外部安全系统提供的运行/制动相关状态。";
        attribute aliases : String = "ATP状态;列控状态";
        attribute priority : String = "条件";
        attribute validityRule : String = "枚举/位集值域固定;需有效位和时间戳";
        attribute faultStrategy : String = "SafeFallback";
    }
    item def I_ITM_STA_028 {
        attribute itemCode : String = "ITM-STA-028";
        attribute chineseName : String = "双向DC/DC状态";
        attribute englishName : String = "DCDCState";
        attribute family : String = "状态/故障";
        attribute domain : String = "储能";
        attribute datatype : String = "Enum";
        attribute unitOrMedium : String = "无";
        attribute semanticDefinition : String = "双向DC/DC待机/充电/放电/故障等状态。";
        attribute aliases : String = "DC/DC模式;ESS变流状态";
        attribute priority : String = "核心";
        attribute validityRule : String = "枚举/位集值域固定;需有效位和时间戳";
        attribute faultStrategy : String = "DegradeAvailability";
    }
    item def I_ITM_STA_029 {
        attribute itemCode : String = "ITM-STA-029";
        attribute chineseName : String = "双向DC/DC故障状态";
        attribute englishName : String = "DCDCFault";
        attribute family : String = "状态/故障";
        attribute domain : String = "储能";
        attribute datatype : String = "Enum/Bitset";
        attribute unitOrMedium : String = "无";
        attribute semanticDefinition : String = "双向DC/DC保护/故障集合。";
        attribute aliases : String = "DC/DC故障";
        attribute priority : String = "核心";
        attribute validityRule : String = "枚举/位集值域固定;需有效位和时间戳";
        attribute faultStrategy : String = "SafeFallback";
    }
    item def I_ITM_STA_030 {
        attribute itemCode : String = "ITM-STA-030";
        attribute chineseName : String = "储能系统可用状态";
        attribute englishName : String = "ESSAvailability";
        attribute family : String = "状态/故障";
        attribute domain : String = "储能";
        attribute datatype : String = "Boolean";
        attribute unitOrMedium : String = "无";
        attribute semanticDefinition : String = "储能支路是否可以接受或释放功率。";
        attribute aliases : String = "ESS可用;储能可用";
        attribute priority : String = "核心";
        attribute validityRule : String = "枚举/位集值域固定;需有效位和时间戳";
        attribute faultStrategy : String = "DegradeAvailability";
    }
    item def I_ITM_STA_031 {
        attribute itemCode : String = "ITM-STA-031";
        attribute chineseName : String = "储能系统故障状态";
        attribute englishName : String = "ESSFault";
        attribute family : String = "状态/故障";
        attribute domain : String = "储能";
        attribute datatype : String = "Enum/Bitset";
        attribute unitOrMedium : String = "无";
        attribute semanticDefinition : String = "储能支路故障集合。";
        attribute aliases : String = "ESS故障;超级电容系统故障";
        attribute priority : String = "核心";
        attribute validityRule : String = "枚举/位集值域固定;需有效位和时间戳";
        attribute faultStrategy : String = "SafeFallback";
    }
    item def I_ITM_STA_032 {
        attribute itemCode : String = "ITM-STA-032";
        attribute chineseName : String = "储能主接触器状态";
        attribute englishName : String = "ESSContactorState";
        attribute family : String = "状态/故障";
        attribute domain : String = "储能";
        attribute datatype : String = "Enum";
        attribute unitOrMedium : String = "无";
        attribute semanticDefinition : String = "储能主接触器分/合/故障状态。";
        attribute aliases : String = "ESS接触器状态";
        attribute priority : String = "核心";
        attribute validityRule : String = "枚举/位集值域固定;需有效位和时间戳";
        attribute faultStrategy : String = "SafeFallback";
    }
    item def I_ITM_STA_033 {
        attribute itemCode : String = "ITM-STA-033";
        attribute chineseName : String = "储能预充电状态";
        attribute englishName : String = "ESSPrechargeState";
        attribute family : String = "状态/故障";
        attribute domain : String = "储能";
        attribute datatype : String = "Enum";
        attribute unitOrMedium : String = "无";
        attribute semanticDefinition : String = "储能预充电未开始/进行中/完成/故障状态。";
        attribute aliases : String = "ESS预充状态";
        attribute priority : String = "核心";
        attribute validityRule : String = "枚举/位集值域固定;需有效位和时间戳";
        attribute faultStrategy : String = "SafeFallback";
    }
    item def I_ITM_STA_034 {
        attribute itemCode : String = "ITM-STA-034";
        attribute chineseName : String = "储能保护跳闸状态";
        attribute englishName : String = "ESSProtectionTripState";
        attribute family : String = "状态/故障";
        attribute domain : String = "储能";
        attribute datatype : String = "Boolean/Enum";
        attribute unitOrMedium : String = "无";
        attribute semanticDefinition : String = "储能支路检测保护组件的跳闸/闭锁状态。";
        attribute aliases : String = "ESS保护;储能跳闸";
        attribute priority : String = "核心";
        attribute validityRule : String = "枚举/位集值域固定;需有效位和时间戳";
        attribute faultStrategy : String = "SafeFallback";
    }
    item def I_ITM_STA_035 {
        attribute itemCode : String = "ITM-STA-035";
        attribute chineseName : String = "能量计量有效状态";
        attribute englishName : String = "EnergyMeasurementValidity";
        attribute family : String = "状态/故障";
        attribute domain : String = "能量统计";
        attribute datatype : String = "Boolean";
        attribute unitOrMedium : String = "无";
        attribute semanticDefinition : String = "能量计量数据是否有效、完整且未超时。";
        attribute aliases : String = "能量计有效位";
        attribute priority : String = "条件";
        attribute validityRule : String = "枚举/位集值域固定;需有效位和时间戳";
        attribute faultStrategy : String = "QualityFlag";
    }
    item def I_ITM_STA_036 {
        attribute itemCode : String = "ITM-STA-036";
        attribute chineseName : String = "制动控制接触器状态";
        attribute englishName : String = "BrakeControlContactorState";
        attribute family : String = "状态/故障";
        attribute domain : String = "制动";
        attribute datatype : String = "Enum";
        attribute unitOrMedium : String = "无";
        attribute semanticDefinition : String = "制动控制接触器断开/闭合/故障状态。";
        attribute aliases : String = "EBCU接触器状态";
        attribute priority : String = "条件";
        attribute validityRule : String = "状态枚举值域固定;需有效位";
        attribute faultStrategy : String = "SafeFallback";
    }
}

package PortDefinitions {
    private import ItemDefinitions::*;
    port def PT_PT_ACC_001 {
        out item payload : I_ITM_ACC_001;
    }
    port def PT_PT_ACC_002 {
        out item payload : I_ITM_ACC_002;
    }
    port def PT_PT_ACC_003 {
        out item payload : I_ITM_ACC_003;
    }
    port def PT_PT_ACC_004 {
        out item payload : I_ITM_ACC_004;
    }
    port def PT_PT_ACC_005 {
        out item payload : I_ITM_ACC_005;
    }
    port def PT_PT_ACC_006 {
        out item payload : I_ITM_ACC_006;
    }
    port def PT_PT_ACC_007 {
        out item payload : I_ITM_ACC_007;
    }
    port def PT_PT_ACC_008 {
        out item payload : I_ITM_ACC_008;
    }
    port def PT_PT_ACC_009 {
        out item payload : I_ITM_ACC_009;
    }
    port def PT_PT_ACC_010 {
        out item payload : I_ITM_ACC_010;
    }
    port def PT_PT_ACC_011 {
        out item payload : I_ITM_ACC_011;
    }
    port def PT_PT_ACC_012 {
        out item payload : I_ITM_ACC_012;
    }
    port def PT_PT_ACC_013 {
        out item payload : I_ITM_ACC_013;
    }
    port def PT_PT_ACC_014 {
        out item payload : I_ITM_ACC_014;
    }
    port def PT_PT_ACC_015 {
        out item payload : I_ITM_ACC_015;
    }
    port def PT_PT_CMD_001 {
        out item payload : I_ITM_CMD_001;
    }
    port def PT_PT_CMD_002 {
        out item payload : I_ITM_CMD_002;
    }
    port def PT_PT_CMD_003 {
        out item payload : I_ITM_CMD_003;
    }
    port def PT_PT_CMD_004 {
        out item payload : I_ITM_CMD_004;
    }
    port def PT_PT_CMD_005 {
        out item payload : I_ITM_CMD_005;
    }
    port def PT_PT_CMD_006 {
        out item payload : I_ITM_CMD_006;
    }
    port def PT_PT_CMD_007 {
        out item payload : I_ITM_CMD_007;
    }
    port def PT_PT_CMD_008 {
        out item payload : I_ITM_CMD_008;
    }
    port def PT_PT_CMD_009 {
        out item payload : I_ITM_CMD_009;
    }
    port def PT_PT_CMD_010 {
        out item payload : I_ITM_CMD_010;
    }
    port def PT_PT_CMD_011 {
        out item payload : I_ITM_CMD_011;
    }
    port def PT_PT_CMD_012 {
        out item payload : I_ITM_CMD_012;
    }
    port def PT_PT_CMD_013 {
        out item payload : I_ITM_CMD_013;
    }
    port def PT_PT_CMD_014 {
        out item payload : I_ITM_CMD_014;
    }
    port def PT_PT_CMD_015 {
        out item payload : I_ITM_CMD_015;
    }
    port def PT_PT_CMD_016 {
        out item payload : I_ITM_CMD_016;
    }
    port def PT_PT_CMD_017 {
        out item payload : I_ITM_CMD_017;
    }
    port def PT_PT_CMD_018 {
        out item payload : I_ITM_CMD_018;
    }
    port def PT_PT_CMD_019 {
        out item payload : I_ITM_CMD_019;
    }
    port def PT_PT_CMD_020 {
        out item payload : I_ITM_CMD_020;
    }
    port def PT_PT_CMD_021 {
        out item payload : I_ITM_CMD_021;
    }
    port def PT_PT_CMD_022 {
        out item payload : I_ITM_CMD_022;
    }
    port def PT_PT_CMD_023 {
        out item payload : I_ITM_CMD_023;
    }
    port def PT_PT_CMD_024 {
        out item payload : I_ITM_CMD_024;
    }
    port def PT_PT_CMD_025 {
        out item payload : I_ITM_CMD_025;
    }
    port def PT_PT_CMD_026 {
        out item payload : I_ITM_CMD_026;
    }
    port def PT_PT_CMD_027 {
        out item payload : I_ITM_CMD_027;
    }
    port def PT_PT_CMD_028 {
        out item payload : I_ITM_CMD_028;
    }
    port def PT_PT_CMD_029 {
        out item payload : I_ITM_CMD_029;
    }
    port def PT_PT_CMD_030 {
        out item payload : I_ITM_CMD_030;
    }
    port def PT_PT_CMD_031 {
        out item payload : I_ITM_CMD_031;
    }
    port def PT_PT_CMD_032 {
        out item payload : I_ITM_CMD_032;
    }
    port def PT_PT_LIM_001 {
        out item payload : I_ITM_LIM_001;
    }
    port def PT_PT_LIM_002 {
        out item payload : I_ITM_LIM_002;
    }
    port def PT_PT_LIM_003 {
        out item payload : I_ITM_LIM_003;
    }
    port def PT_PT_LIM_004 {
        out item payload : I_ITM_LIM_004;
    }
    port def PT_PT_LIM_005 {
        out item payload : I_ITM_LIM_005;
    }
    port def PT_PT_LIM_006 {
        out item payload : I_ITM_LIM_006;
    }
    port def PT_PT_LIM_007 {
        out item payload : I_ITM_LIM_007;
    }
    port def PT_PT_LIM_008 {
        out item payload : I_ITM_LIM_008;
    }
    port def PT_PT_LIM_009 {
        out item payload : I_ITM_LIM_009;
    }
    port def PT_PT_LIM_010 {
        out item payload : I_ITM_LIM_010;
    }
    port def PT_PT_LIM_011 {
        out item payload : I_ITM_LIM_011;
    }
    port def PT_PT_LIM_012 {
        out item payload : I_ITM_LIM_012;
    }
    port def PT_PT_LIM_013 {
        out item payload : I_ITM_LIM_013;
    }
    port def PT_PT_LIM_014 {
        out item payload : I_ITM_LIM_014;
    }
    port def PT_PT_MEA_001 {
        out item payload : I_ITM_MEA_001;
    }
    port def PT_PT_MEA_002 {
        out item payload : I_ITM_MEA_002;
    }
    port def PT_PT_MEA_003 {
        out item payload : I_ITM_MEA_003;
    }
    port def PT_PT_MEA_004 {
        out item payload : I_ITM_MEA_004;
    }
    port def PT_PT_MEA_005 {
        out item payload : I_ITM_MEA_005;
    }
    port def PT_PT_MEA_006 {
        out item payload : I_ITM_MEA_006;
    }
    port def PT_PT_MEA_007 {
        out item payload : I_ITM_MEA_007;
    }
    port def PT_PT_MEA_008 {
        out item payload : I_ITM_MEA_008;
    }
    port def PT_PT_MEA_009 {
        out item payload : I_ITM_MEA_009;
    }
    port def PT_PT_MEA_010 {
        out item payload : I_ITM_MEA_010;
    }
    port def PT_PT_MEA_011 {
        out item payload : I_ITM_MEA_011;
    }
    port def PT_PT_MEA_012 {
        out item payload : I_ITM_MEA_012;
    }
    port def PT_PT_MEA_013 {
        out item payload : I_ITM_MEA_013;
    }
    port def PT_PT_MEA_014 {
        out item payload : I_ITM_MEA_014;
    }
    port def PT_PT_MEA_015 {
        out item payload : I_ITM_MEA_015;
    }
    port def PT_PT_MEA_016 {
        out item payload : I_ITM_MEA_016;
    }
    port def PT_PT_MEA_017 {
        out item payload : I_ITM_MEA_017;
    }
    port def PT_PT_MEA_018 {
        out item payload : I_ITM_MEA_018;
    }
    port def PT_PT_MEA_019 {
        out item payload : I_ITM_MEA_019;
    }
    port def PT_PT_MEA_020 {
        out item payload : I_ITM_MEA_020;
    }
    port def PT_PT_MEA_021 {
        out item payload : I_ITM_MEA_021;
    }
    port def PT_PT_MEA_022 {
        out item payload : I_ITM_MEA_022;
    }
    port def PT_PT_MEA_023 {
        out item payload : I_ITM_MEA_023;
    }
    port def PT_PT_MEA_024 {
        out item payload : I_ITM_MEA_024;
    }
    port def PT_PT_MEA_025 {
        out item payload : I_ITM_MEA_025;
    }
    port def PT_PT_MEA_026 {
        out item payload : I_ITM_MEA_026;
    }
    port def PT_PT_MEA_027 {
        out item payload : I_ITM_MEA_027;
    }
    port def PT_PT_MEA_028 {
        out item payload : I_ITM_MEA_028;
    }
    port def PT_PT_MEA_029 {
        out item payload : I_ITM_MEA_029;
    }
    port def PT_PT_MEA_030 {
        out item payload : I_ITM_MEA_030;
    }
    port def PT_PT_MEA_031 {
        out item payload : I_ITM_MEA_031;
    }
    port def PT_PT_PHY_001 {
        inout item payload : I_ITM_PHY_001;
    }
    port def PT_PT_PHY_002 {
        inout item payload : I_ITM_PHY_002;
    }
    port def PT_PT_PHY_003 {
        inout item payload : I_ITM_PHY_003;
    }
    port def PT_PT_PHY_004 {
        inout item payload : I_ITM_PHY_004;
    }
    port def PT_PT_PHY_005 {
        inout item payload : I_ITM_PHY_005;
    }
    port def PT_PT_PHY_006 {
        inout item payload : I_ITM_PHY_006;
    }
    port def PT_PT_PHY_007 {
        inout item payload : I_ITM_PHY_007;
    }
    port def PT_PT_PHY_008 {
        inout item payload : I_ITM_PHY_008;
    }
    port def PT_PT_PHY_009 {
        inout item payload : I_ITM_PHY_009;
    }
    port def PT_PT_PHY_010 {
        inout item payload : I_ITM_PHY_010;
    }
    port def PT_PT_PHY_011 {
        inout item payload : I_ITM_PHY_011;
    }
    port def PT_PT_PHY_012 {
        inout item payload : I_ITM_PHY_012;
    }
    port def PT_PT_PHY_013 {
        inout item payload : I_ITM_PHY_013;
    }
    port def PT_PT_PHY_014 {
        inout item payload : I_ITM_PHY_014;
    }
    port def PT_PT_PHY_015 {
        inout item payload : I_ITM_PHY_015;
    }
    port def PT_PT_PHY_016 {
        inout item payload : I_ITM_PHY_016;
    }
    port def PT_PT_STA_001 {
        out item payload : I_ITM_STA_001;
    }
    port def PT_PT_STA_002 {
        out item payload : I_ITM_STA_002;
    }
    port def PT_PT_STA_003 {
        out item payload : I_ITM_STA_003;
    }
    port def PT_PT_STA_004 {
        out item payload : I_ITM_STA_004;
    }
    port def PT_PT_STA_005 {
        out item payload : I_ITM_STA_005;
    }
    port def PT_PT_STA_006 {
        out item payload : I_ITM_STA_006;
    }
    port def PT_PT_STA_007 {
        out item payload : I_ITM_STA_007;
    }
    port def PT_PT_STA_008 {
        out item payload : I_ITM_STA_008;
    }
    port def PT_PT_STA_009 {
        out item payload : I_ITM_STA_009;
    }
    port def PT_PT_STA_010 {
        out item payload : I_ITM_STA_010;
    }
    port def PT_PT_STA_011 {
        out item payload : I_ITM_STA_011;
    }
    port def PT_PT_STA_012 {
        out item payload : I_ITM_STA_012;
    }
    port def PT_PT_STA_013 {
        out item payload : I_ITM_STA_013;
    }
    port def PT_PT_STA_014 {
        out item payload : I_ITM_STA_014;
    }
    port def PT_PT_STA_015 {
        out item payload : I_ITM_STA_015;
    }
    port def PT_PT_STA_016 {
        out item payload : I_ITM_STA_016;
    }
    port def PT_PT_STA_017 {
        out item payload : I_ITM_STA_017;
    }
    port def PT_PT_STA_018 {
        out item payload : I_ITM_STA_018;
    }
    port def PT_PT_STA_019 {
        out item payload : I_ITM_STA_019;
    }
    port def PT_PT_STA_020 {
        out item payload : I_ITM_STA_020;
    }
    port def PT_PT_STA_021 {
        out item payload : I_ITM_STA_021;
    }
    port def PT_PT_STA_022 {
        out item payload : I_ITM_STA_022;
    }
    port def PT_PT_STA_023 {
        out item payload : I_ITM_STA_023;
    }
    port def PT_PT_STA_024 {
        out item payload : I_ITM_STA_024;
    }
    port def PT_PT_STA_025 {
        out item payload : I_ITM_STA_025;
    }
    port def PT_PT_STA_026 {
        out item payload : I_ITM_STA_026;
    }
    port def PT_PT_STA_027 {
        out item payload : I_ITM_STA_027;
    }
    port def PT_PT_STA_028 {
        out item payload : I_ITM_STA_028;
    }
    port def PT_PT_STA_029 {
        out item payload : I_ITM_STA_029;
    }
    port def PT_PT_STA_030 {
        out item payload : I_ITM_STA_030;
    }
    port def PT_PT_STA_031 {
        out item payload : I_ITM_STA_031;
    }
    port def PT_PT_STA_032 {
        out item payload : I_ITM_STA_032;
    }
    port def PT_PT_STA_033 {
        out item payload : I_ITM_STA_033;
    }
    port def PT_PT_STA_034 {
        out item payload : I_ITM_STA_034;
    }
    port def PT_PT_STA_035 {
        out item payload : I_ITM_STA_035;
    }
    port def PT_PT_STA_036 {
        out item payload : I_ITM_STA_036;
    }
}

package InterfaceDefinitions {
    private import ItemDefinitions::*;
    private import PortDefinitions::*;
    interface def IF_IF_ACC_001 {
        end source : PT_PT_ACC_001;
        end target : ~PT_PT_ACC_001;
        flow of I_ITM_ACC_001 from source.payload to target.payload;
    }
    interface def IF_IF_ACC_002 {
        end source : PT_PT_ACC_002;
        end target : ~PT_PT_ACC_002;
        flow of I_ITM_ACC_002 from source.payload to target.payload;
    }
    interface def IF_IF_ACC_003 {
        end source : PT_PT_ACC_003;
        end target : ~PT_PT_ACC_003;
        flow of I_ITM_ACC_003 from source.payload to target.payload;
    }
    interface def IF_IF_ACC_004 {
        end source : PT_PT_ACC_004;
        end target : ~PT_PT_ACC_004;
        flow of I_ITM_ACC_004 from source.payload to target.payload;
    }
    interface def IF_IF_ACC_005 {
        end source : PT_PT_ACC_005;
        end target : ~PT_PT_ACC_005;
        flow of I_ITM_ACC_005 from source.payload to target.payload;
    }
    interface def IF_IF_ACC_006 {
        end source : PT_PT_ACC_006;
        end target : ~PT_PT_ACC_006;
        flow of I_ITM_ACC_006 from source.payload to target.payload;
    }
    interface def IF_IF_ACC_007 {
        end source : PT_PT_ACC_007;
        end target : ~PT_PT_ACC_007;
        flow of I_ITM_ACC_007 from source.payload to target.payload;
    }
    interface def IF_IF_ACC_008 {
        end source : PT_PT_ACC_008;
        end target : ~PT_PT_ACC_008;
        flow of I_ITM_ACC_008 from source.payload to target.payload;
    }
    interface def IF_IF_ACC_009 {
        end source : PT_PT_ACC_009;
        end target : ~PT_PT_ACC_009;
        flow of I_ITM_ACC_009 from source.payload to target.payload;
    }
    interface def IF_IF_ACC_010 {
        end source : PT_PT_ACC_010;
        end target : ~PT_PT_ACC_010;
        flow of I_ITM_ACC_010 from source.payload to target.payload;
    }
    interface def IF_IF_ACC_011 {
        end source : PT_PT_ACC_011;
        end target : ~PT_PT_ACC_011;
        flow of I_ITM_ACC_011 from source.payload to target.payload;
    }
    interface def IF_IF_ACC_012 {
        end source : PT_PT_ACC_012;
        end target : ~PT_PT_ACC_012;
        flow of I_ITM_ACC_012 from source.payload to target.payload;
    }
    interface def IF_IF_ACC_013 {
        end source : PT_PT_ACC_013;
        end target : ~PT_PT_ACC_013;
        flow of I_ITM_ACC_013 from source.payload to target.payload;
    }
    interface def IF_IF_ACC_014 {
        end source : PT_PT_ACC_014;
        end target : ~PT_PT_ACC_014;
        flow of I_ITM_ACC_014 from source.payload to target.payload;
    }
    interface def IF_IF_ACC_015 {
        end source : PT_PT_ACC_015;
        end target : ~PT_PT_ACC_015;
        flow of I_ITM_ACC_015 from source.payload to target.payload;
    }
    interface def IF_IF_CMD_001 {
        end source : PT_PT_CMD_001;
        end target : ~PT_PT_CMD_001;
        flow of I_ITM_CMD_001 from source.payload to target.payload;
    }
    interface def IF_IF_CMD_002 {
        end source : PT_PT_CMD_002;
        end target : ~PT_PT_CMD_002;
        flow of I_ITM_CMD_002 from source.payload to target.payload;
    }
    interface def IF_IF_CMD_003 {
        end source : PT_PT_CMD_003;
        end target : ~PT_PT_CMD_003;
        flow of I_ITM_CMD_003 from source.payload to target.payload;
    }
    interface def IF_IF_CMD_004 {
        end source : PT_PT_CMD_004;
        end target : ~PT_PT_CMD_004;
        flow of I_ITM_CMD_004 from source.payload to target.payload;
    }
    interface def IF_IF_CMD_005 {
        end source : PT_PT_CMD_005;
        end target : ~PT_PT_CMD_005;
        flow of I_ITM_CMD_005 from source.payload to target.payload;
    }
    interface def IF_IF_CMD_006 {
        end source : PT_PT_CMD_006;
        end target : ~PT_PT_CMD_006;
        flow of I_ITM_CMD_006 from source.payload to target.payload;
    }
    interface def IF_IF_CMD_007 {
        end source : PT_PT_CMD_007;
        end target : ~PT_PT_CMD_007;
        flow of I_ITM_CMD_007 from source.payload to target.payload;
    }
    interface def IF_IF_CMD_008 {
        end source : PT_PT_CMD_008;
        end target : ~PT_PT_CMD_008;
        flow of I_ITM_CMD_008 from source.payload to target.payload;
    }
    interface def IF_IF_CMD_009 {
        end source : PT_PT_CMD_009;
        end target : ~PT_PT_CMD_009;
        flow of I_ITM_CMD_009 from source.payload to target.payload;
    }
    interface def IF_IF_CMD_010 {
        end source : PT_PT_CMD_010;
        end target : ~PT_PT_CMD_010;
        flow of I_ITM_CMD_010 from source.payload to target.payload;
    }
    interface def IF_IF_CMD_011 {
        end source : PT_PT_CMD_011;
        end target : ~PT_PT_CMD_011;
        flow of I_ITM_CMD_011 from source.payload to target.payload;
    }
    interface def IF_IF_CMD_012 {
        end source : PT_PT_CMD_012;
        end target : ~PT_PT_CMD_012;
        flow of I_ITM_CMD_012 from source.payload to target.payload;
    }
    interface def IF_IF_CMD_013 {
        end source : PT_PT_CMD_013;
        end target : ~PT_PT_CMD_013;
        flow of I_ITM_CMD_013 from source.payload to target.payload;
    }
    interface def IF_IF_CMD_014 {
        end source : PT_PT_CMD_014;
        end target : ~PT_PT_CMD_014;
        flow of I_ITM_CMD_014 from source.payload to target.payload;
    }
    interface def IF_IF_CMD_015 {
        end source : PT_PT_CMD_015;
        end target : ~PT_PT_CMD_015;
        flow of I_ITM_CMD_015 from source.payload to target.payload;
    }
    interface def IF_IF_CMD_016 {
        end source : PT_PT_CMD_016;
        end target : ~PT_PT_CMD_016;
        flow of I_ITM_CMD_016 from source.payload to target.payload;
    }
    interface def IF_IF_CMD_017 {
        end source : PT_PT_CMD_017;
        end target : ~PT_PT_CMD_017;
        flow of I_ITM_CMD_017 from source.payload to target.payload;
    }
    interface def IF_IF_CMD_018 {
        end source : PT_PT_CMD_018;
        end target : ~PT_PT_CMD_018;
        flow of I_ITM_CMD_018 from source.payload to target.payload;
    }
    interface def IF_IF_CMD_019 {
        end source : PT_PT_CMD_019;
        end target : ~PT_PT_CMD_019;
        flow of I_ITM_CMD_019 from source.payload to target.payload;
    }
    interface def IF_IF_CMD_020 {
        end source : PT_PT_CMD_020;
        end target : ~PT_PT_CMD_020;
        flow of I_ITM_CMD_020 from source.payload to target.payload;
    }
    interface def IF_IF_CMD_021 {
        end source : PT_PT_CMD_021;
        end target : ~PT_PT_CMD_021;
        flow of I_ITM_CMD_021 from source.payload to target.payload;
    }
    interface def IF_IF_CMD_022 {
        end source : PT_PT_CMD_022;
        end target : ~PT_PT_CMD_022;
        flow of I_ITM_CMD_022 from source.payload to target.payload;
    }
    interface def IF_IF_CMD_023 {
        end source : PT_PT_CMD_023;
        end target : ~PT_PT_CMD_023;
        flow of I_ITM_CMD_023 from source.payload to target.payload;
    }
    interface def IF_IF_CMD_024 {
        end source : PT_PT_CMD_024;
        end target : ~PT_PT_CMD_024;
        flow of I_ITM_CMD_024 from source.payload to target.payload;
    }
    interface def IF_IF_CMD_025 {
        end source : PT_PT_CMD_025;
        end target : ~PT_PT_CMD_025;
        flow of I_ITM_CMD_025 from source.payload to target.payload;
    }
    interface def IF_IF_CMD_026 {
        end source : PT_PT_CMD_026;
        end target : ~PT_PT_CMD_026;
        flow of I_ITM_CMD_026 from source.payload to target.payload;
    }
    interface def IF_IF_CMD_027 {
        end source : PT_PT_CMD_027;
        end target : ~PT_PT_CMD_027;
        flow of I_ITM_CMD_027 from source.payload to target.payload;
    }
    interface def IF_IF_CMD_028 {
        end source : PT_PT_CMD_028;
        end target : ~PT_PT_CMD_028;
        flow of I_ITM_CMD_028 from source.payload to target.payload;
    }
    interface def IF_IF_CMD_029 {
        end source : PT_PT_CMD_029;
        end target : ~PT_PT_CMD_029;
        flow of I_ITM_CMD_029 from source.payload to target.payload;
    }
    interface def IF_IF_CMD_030 {
        end source : PT_PT_CMD_030;
        end target : ~PT_PT_CMD_030;
        flow of I_ITM_CMD_030 from source.payload to target.payload;
    }
    interface def IF_IF_CMD_031 {
        end source : PT_PT_CMD_031;
        end target : ~PT_PT_CMD_031;
        flow of I_ITM_CMD_031 from source.payload to target.payload;
    }
    interface def IF_IF_CMD_032 {
        end source : PT_PT_CMD_032;
        end target : ~PT_PT_CMD_032;
        flow of I_ITM_CMD_032 from source.payload to target.payload;
    }
    interface def IF_IF_LIM_001 {
        end source : PT_PT_LIM_001;
        end target : ~PT_PT_LIM_001;
        flow of I_ITM_LIM_001 from source.payload to target.payload;
    }
    interface def IF_IF_LIM_002 {
        end source : PT_PT_LIM_002;
        end target : ~PT_PT_LIM_002;
        flow of I_ITM_LIM_002 from source.payload to target.payload;
    }
    interface def IF_IF_LIM_003 {
        end source : PT_PT_LIM_003;
        end target : ~PT_PT_LIM_003;
        flow of I_ITM_LIM_003 from source.payload to target.payload;
    }
    interface def IF_IF_LIM_004 {
        end source : PT_PT_LIM_004;
        end target : ~PT_PT_LIM_004;
        flow of I_ITM_LIM_004 from source.payload to target.payload;
    }
    interface def IF_IF_LIM_005 {
        end source : PT_PT_LIM_005;
        end target : ~PT_PT_LIM_005;
        flow of I_ITM_LIM_005 from source.payload to target.payload;
    }
    interface def IF_IF_LIM_006 {
        end source : PT_PT_LIM_006;
        end target : ~PT_PT_LIM_006;
        flow of I_ITM_LIM_006 from source.payload to target.payload;
    }
    interface def IF_IF_LIM_007 {
        end source : PT_PT_LIM_007;
        end target : ~PT_PT_LIM_007;
        flow of I_ITM_LIM_007 from source.payload to target.payload;
    }
    interface def IF_IF_LIM_008 {
        end source : PT_PT_LIM_008;
        end target : ~PT_PT_LIM_008;
        flow of I_ITM_LIM_008 from source.payload to target.payload;
    }
    interface def IF_IF_LIM_009 {
        end source : PT_PT_LIM_009;
        end target : ~PT_PT_LIM_009;
        flow of I_ITM_LIM_009 from source.payload to target.payload;
    }
    interface def IF_IF_LIM_010 {
        end source : PT_PT_LIM_010;
        end target : ~PT_PT_LIM_010;
        flow of I_ITM_LIM_010 from source.payload to target.payload;
    }
    interface def IF_IF_LIM_011 {
        end source : PT_PT_LIM_011;
        end target : ~PT_PT_LIM_011;
        flow of I_ITM_LIM_011 from source.payload to target.payload;
    }
    interface def IF_IF_LIM_012 {
        end source : PT_PT_LIM_012;
        end target : ~PT_PT_LIM_012;
        flow of I_ITM_LIM_012 from source.payload to target.payload;
    }
    interface def IF_IF_LIM_013 {
        end source : PT_PT_LIM_013;
        end target : ~PT_PT_LIM_013;
        flow of I_ITM_LIM_013 from source.payload to target.payload;
    }
    interface def IF_IF_LIM_014 {
        end source : PT_PT_LIM_014;
        end target : ~PT_PT_LIM_014;
        flow of I_ITM_LIM_014 from source.payload to target.payload;
    }
    interface def IF_IF_MEA_001 {
        end source : PT_PT_MEA_001;
        end target : ~PT_PT_MEA_001;
        flow of I_ITM_MEA_001 from source.payload to target.payload;
    }
    interface def IF_IF_MEA_002 {
        end source : PT_PT_MEA_002;
        end target : ~PT_PT_MEA_002;
        flow of I_ITM_MEA_002 from source.payload to target.payload;
    }
    interface def IF_IF_MEA_003 {
        end source : PT_PT_MEA_003;
        end target : ~PT_PT_MEA_003;
        flow of I_ITM_MEA_003 from source.payload to target.payload;
    }
    interface def IF_IF_MEA_004 {
        end source : PT_PT_MEA_004;
        end target : ~PT_PT_MEA_004;
        flow of I_ITM_MEA_004 from source.payload to target.payload;
    }
    interface def IF_IF_MEA_005 {
        end source : PT_PT_MEA_005;
        end target : ~PT_PT_MEA_005;
        flow of I_ITM_MEA_005 from source.payload to target.payload;
    }
    interface def IF_IF_MEA_006 {
        end source : PT_PT_MEA_006;
        end target : ~PT_PT_MEA_006;
        flow of I_ITM_MEA_006 from source.payload to target.payload;
    }
    interface def IF_IF_MEA_007 {
        end source : PT_PT_MEA_007;
        end target : ~PT_PT_MEA_007;
        flow of I_ITM_MEA_007 from source.payload to target.payload;
    }
    interface def IF_IF_MEA_008 {
        end source : PT_PT_MEA_008;
        end target : ~PT_PT_MEA_008;
        flow of I_ITM_MEA_008 from source.payload to target.payload;
    }
    interface def IF_IF_MEA_009 {
        end source : PT_PT_MEA_009;
        end target : ~PT_PT_MEA_009;
        flow of I_ITM_MEA_009 from source.payload to target.payload;
    }
    interface def IF_IF_MEA_010 {
        end source : PT_PT_MEA_010;
        end target : ~PT_PT_MEA_010;
        flow of I_ITM_MEA_010 from source.payload to target.payload;
    }
    interface def IF_IF_MEA_011 {
        end source : PT_PT_MEA_011;
        end target : ~PT_PT_MEA_011;
        flow of I_ITM_MEA_011 from source.payload to target.payload;
    }
    interface def IF_IF_MEA_012 {
        end source : PT_PT_MEA_012;
        end target : ~PT_PT_MEA_012;
        flow of I_ITM_MEA_012 from source.payload to target.payload;
    }
    interface def IF_IF_MEA_013 {
        end source : PT_PT_MEA_013;
        end target : ~PT_PT_MEA_013;
        flow of I_ITM_MEA_013 from source.payload to target.payload;
    }
    interface def IF_IF_MEA_014 {
        end source : PT_PT_MEA_014;
        end target : ~PT_PT_MEA_014;
        flow of I_ITM_MEA_014 from source.payload to target.payload;
    }
    interface def IF_IF_MEA_015 {
        end source : PT_PT_MEA_015;
        end target : ~PT_PT_MEA_015;
        flow of I_ITM_MEA_015 from source.payload to target.payload;
    }
    interface def IF_IF_MEA_016 {
        end source : PT_PT_MEA_016;
        end target : ~PT_PT_MEA_016;
        flow of I_ITM_MEA_016 from source.payload to target.payload;
    }
    interface def IF_IF_MEA_017 {
        end source : PT_PT_MEA_017;
        end target : ~PT_PT_MEA_017;
        flow of I_ITM_MEA_017 from source.payload to target.payload;
    }
    interface def IF_IF_MEA_018 {
        end source : PT_PT_MEA_018;
        end target : ~PT_PT_MEA_018;
        flow of I_ITM_MEA_018 from source.payload to target.payload;
    }
    interface def IF_IF_MEA_019 {
        end source : PT_PT_MEA_019;
        end target : ~PT_PT_MEA_019;
        flow of I_ITM_MEA_019 from source.payload to target.payload;
    }
    interface def IF_IF_MEA_020 {
        end source : PT_PT_MEA_020;
        end target : ~PT_PT_MEA_020;
        flow of I_ITM_MEA_020 from source.payload to target.payload;
    }
    interface def IF_IF_MEA_021 {
        end source : PT_PT_MEA_021;
        end target : ~PT_PT_MEA_021;
        flow of I_ITM_MEA_021 from source.payload to target.payload;
    }
    interface def IF_IF_MEA_022 {
        end source : PT_PT_MEA_022;
        end target : ~PT_PT_MEA_022;
        flow of I_ITM_MEA_022 from source.payload to target.payload;
    }
    interface def IF_IF_MEA_023 {
        end source : PT_PT_MEA_023;
        end target : ~PT_PT_MEA_023;
        flow of I_ITM_MEA_023 from source.payload to target.payload;
    }
    interface def IF_IF_MEA_024 {
        end source : PT_PT_MEA_024;
        end target : ~PT_PT_MEA_024;
        flow of I_ITM_MEA_024 from source.payload to target.payload;
    }
    interface def IF_IF_MEA_025 {
        end source : PT_PT_MEA_025;
        end target : ~PT_PT_MEA_025;
        flow of I_ITM_MEA_025 from source.payload to target.payload;
    }
    interface def IF_IF_MEA_026 {
        end source : PT_PT_MEA_026;
        end target : ~PT_PT_MEA_026;
        flow of I_ITM_MEA_026 from source.payload to target.payload;
    }
    interface def IF_IF_MEA_027 {
        end source : PT_PT_MEA_027;
        end target : ~PT_PT_MEA_027;
        flow of I_ITM_MEA_027 from source.payload to target.payload;
    }
    interface def IF_IF_MEA_028 {
        end source : PT_PT_MEA_028;
        end target : ~PT_PT_MEA_028;
        flow of I_ITM_MEA_028 from source.payload to target.payload;
    }
    interface def IF_IF_MEA_029 {
        end source : PT_PT_MEA_029;
        end target : ~PT_PT_MEA_029;
        flow of I_ITM_MEA_029 from source.payload to target.payload;
    }
    interface def IF_IF_MEA_030 {
        end source : PT_PT_MEA_030;
        end target : ~PT_PT_MEA_030;
        flow of I_ITM_MEA_030 from source.payload to target.payload;
    }
    interface def IF_IF_MEA_031 {
        end source : PT_PT_MEA_031;
        end target : ~PT_PT_MEA_031;
        flow of I_ITM_MEA_031 from source.payload to target.payload;
    }
    interface def IF_IF_PHY_001 {
        end source : PT_PT_PHY_001;
        end target : PT_PT_PHY_001;
        flow of I_ITM_PHY_001 from source.payload to target.payload;
    }
    interface def IF_IF_PHY_002 {
        end source : PT_PT_PHY_002;
        end target : PT_PT_PHY_002;
        flow of I_ITM_PHY_002 from source.payload to target.payload;
    }
    interface def IF_IF_PHY_003 {
        end source : PT_PT_PHY_003;
        end target : PT_PT_PHY_003;
        flow of I_ITM_PHY_003 from source.payload to target.payload;
    }
    interface def IF_IF_PHY_004 {
        end source : PT_PT_PHY_004;
        end target : PT_PT_PHY_004;
        flow of I_ITM_PHY_004 from source.payload to target.payload;
    }
    interface def IF_IF_PHY_005 {
        end source : PT_PT_PHY_005;
        end target : PT_PT_PHY_005;
        flow of I_ITM_PHY_005 from source.payload to target.payload;
    }
    interface def IF_IF_PHY_006 {
        end source : PT_PT_PHY_006;
        end target : PT_PT_PHY_006;
        flow of I_ITM_PHY_006 from source.payload to target.payload;
    }
    interface def IF_IF_PHY_007 {
        end source : PT_PT_PHY_007;
        end target : PT_PT_PHY_007;
        flow of I_ITM_PHY_007 from source.payload to target.payload;
    }
    interface def IF_IF_PHY_008 {
        end source : PT_PT_PHY_008;
        end target : PT_PT_PHY_008;
        flow of I_ITM_PHY_008 from source.payload to target.payload;
    }
    interface def IF_IF_PHY_009 {
        end source : PT_PT_PHY_009;
        end target : PT_PT_PHY_009;
        flow of I_ITM_PHY_009 from source.payload to target.payload;
    }
    interface def IF_IF_PHY_010 {
        end source : PT_PT_PHY_010;
        end target : PT_PT_PHY_010;
        flow of I_ITM_PHY_010 from source.payload to target.payload;
    }
    interface def IF_IF_PHY_011 {
        end source : PT_PT_PHY_011;
        end target : PT_PT_PHY_011;
        flow of I_ITM_PHY_011 from source.payload to target.payload;
    }
    interface def IF_IF_PHY_012 {
        end source : PT_PT_PHY_012;
        end target : PT_PT_PHY_012;
        flow of I_ITM_PHY_012 from source.payload to target.payload;
    }
    interface def IF_IF_PHY_013 {
        end source : PT_PT_PHY_013;
        end target : PT_PT_PHY_013;
        flow of I_ITM_PHY_013 from source.payload to target.payload;
    }
    interface def IF_IF_PHY_014 {
        end source : PT_PT_PHY_014;
        end target : PT_PT_PHY_014;
        flow of I_ITM_PHY_014 from source.payload to target.payload;
    }
    interface def IF_IF_PHY_015 {
        end source : PT_PT_PHY_015;
        end target : PT_PT_PHY_015;
        flow of I_ITM_PHY_015 from source.payload to target.payload;
    }
    interface def IF_IF_PHY_016 {
        end source : PT_PT_PHY_016;
        end target : PT_PT_PHY_016;
        flow of I_ITM_PHY_016 from source.payload to target.payload;
    }
    interface def IF_IF_STA_001 {
        end source : PT_PT_STA_001;
        end target : ~PT_PT_STA_001;
        flow of I_ITM_STA_001 from source.payload to target.payload;
    }
    interface def IF_IF_STA_002 {
        end source : PT_PT_STA_002;
        end target : ~PT_PT_STA_002;
        flow of I_ITM_STA_002 from source.payload to target.payload;
    }
    interface def IF_IF_STA_003 {
        end source : PT_PT_STA_003;
        end target : ~PT_PT_STA_003;
        flow of I_ITM_STA_003 from source.payload to target.payload;
    }
    interface def IF_IF_STA_004 {
        end source : PT_PT_STA_004;
        end target : ~PT_PT_STA_004;
        flow of I_ITM_STA_004 from source.payload to target.payload;
    }
    interface def IF_IF_STA_005 {
        end source : PT_PT_STA_005;
        end target : ~PT_PT_STA_005;
        flow of I_ITM_STA_005 from source.payload to target.payload;
    }
    interface def IF_IF_STA_006 {
        end source : PT_PT_STA_006;
        end target : ~PT_PT_STA_006;
        flow of I_ITM_STA_006 from source.payload to target.payload;
    }
    interface def IF_IF_STA_007 {
        end source : PT_PT_STA_007;
        end target : ~PT_PT_STA_007;
        flow of I_ITM_STA_007 from source.payload to target.payload;
    }
    interface def IF_IF_STA_008 {
        end source : PT_PT_STA_008;
        end target : ~PT_PT_STA_008;
        flow of I_ITM_STA_008 from source.payload to target.payload;
    }
    interface def IF_IF_STA_009 {
        end source : PT_PT_STA_009;
        end target : ~PT_PT_STA_009;
        flow of I_ITM_STA_009 from source.payload to target.payload;
    }
    interface def IF_IF_STA_010 {
        end source : PT_PT_STA_010;
        end target : ~PT_PT_STA_010;
        flow of I_ITM_STA_010 from source.payload to target.payload;
    }
    interface def IF_IF_STA_011 {
        end source : PT_PT_STA_011;
        end target : ~PT_PT_STA_011;
        flow of I_ITM_STA_011 from source.payload to target.payload;
    }
    interface def IF_IF_STA_012 {
        end source : PT_PT_STA_012;
        end target : ~PT_PT_STA_012;
        flow of I_ITM_STA_012 from source.payload to target.payload;
    }
    interface def IF_IF_STA_013 {
        end source : PT_PT_STA_013;
        end target : ~PT_PT_STA_013;
        flow of I_ITM_STA_013 from source.payload to target.payload;
    }
    interface def IF_IF_STA_014 {
        end source : PT_PT_STA_014;
        end target : ~PT_PT_STA_014;
        flow of I_ITM_STA_014 from source.payload to target.payload;
    }
    interface def IF_IF_STA_015 {
        end source : PT_PT_STA_015;
        end target : ~PT_PT_STA_015;
        flow of I_ITM_STA_015 from source.payload to target.payload;
    }
    interface def IF_IF_STA_016 {
        end source : PT_PT_STA_016;
        end target : ~PT_PT_STA_016;
        flow of I_ITM_STA_016 from source.payload to target.payload;
    }
    interface def IF_IF_STA_017 {
        end source : PT_PT_STA_017;
        end target : ~PT_PT_STA_017;
        flow of I_ITM_STA_017 from source.payload to target.payload;
    }
    interface def IF_IF_STA_018 {
        end source : PT_PT_STA_018;
        end target : ~PT_PT_STA_018;
        flow of I_ITM_STA_018 from source.payload to target.payload;
    }
    interface def IF_IF_STA_019 {
        end source : PT_PT_STA_019;
        end target : ~PT_PT_STA_019;
        flow of I_ITM_STA_019 from source.payload to target.payload;
    }
    interface def IF_IF_STA_020 {
        end source : PT_PT_STA_020;
        end target : ~PT_PT_STA_020;
        flow of I_ITM_STA_020 from source.payload to target.payload;
    }
    interface def IF_IF_STA_021 {
        end source : PT_PT_STA_021;
        end target : ~PT_PT_STA_021;
        flow of I_ITM_STA_021 from source.payload to target.payload;
    }
    interface def IF_IF_STA_022 {
        end source : PT_PT_STA_022;
        end target : ~PT_PT_STA_022;
        flow of I_ITM_STA_022 from source.payload to target.payload;
    }
    interface def IF_IF_STA_023 {
        end source : PT_PT_STA_023;
        end target : ~PT_PT_STA_023;
        flow of I_ITM_STA_023 from source.payload to target.payload;
    }
    interface def IF_IF_STA_024 {
        end source : PT_PT_STA_024;
        end target : ~PT_PT_STA_024;
        flow of I_ITM_STA_024 from source.payload to target.payload;
    }
    interface def IF_IF_STA_025 {
        end source : PT_PT_STA_025;
        end target : ~PT_PT_STA_025;
        flow of I_ITM_STA_025 from source.payload to target.payload;
    }
    interface def IF_IF_STA_026 {
        end source : PT_PT_STA_026;
        end target : ~PT_PT_STA_026;
        flow of I_ITM_STA_026 from source.payload to target.payload;
    }
    interface def IF_IF_STA_027 {
        end source : PT_PT_STA_027;
        end target : ~PT_PT_STA_027;
        flow of I_ITM_STA_027 from source.payload to target.payload;
    }
    interface def IF_IF_STA_028 {
        end source : PT_PT_STA_028;
        end target : ~PT_PT_STA_028;
        flow of I_ITM_STA_028 from source.payload to target.payload;
    }
    interface def IF_IF_STA_029 {
        end source : PT_PT_STA_029;
        end target : ~PT_PT_STA_029;
        flow of I_ITM_STA_029 from source.payload to target.payload;
    }
    interface def IF_IF_STA_030 {
        end source : PT_PT_STA_030;
        end target : ~PT_PT_STA_030;
        flow of I_ITM_STA_030 from source.payload to target.payload;
    }
    interface def IF_IF_STA_031 {
        end source : PT_PT_STA_031;
        end target : ~PT_PT_STA_031;
        flow of I_ITM_STA_031 from source.payload to target.payload;
    }
    interface def IF_IF_STA_032 {
        end source : PT_PT_STA_032;
        end target : ~PT_PT_STA_032;
        flow of I_ITM_STA_032 from source.payload to target.payload;
    }
    interface def IF_IF_STA_033 {
        end source : PT_PT_STA_033;
        end target : ~PT_PT_STA_033;
        flow of I_ITM_STA_033 from source.payload to target.payload;
    }
    interface def IF_IF_STA_034 {
        end source : PT_PT_STA_034;
        end target : ~PT_PT_STA_034;
        flow of I_ITM_STA_034 from source.payload to target.payload;
    }
    interface def IF_IF_STA_035 {
        end source : PT_PT_STA_035;
        end target : ~PT_PT_STA_035;
        flow of I_ITM_STA_035 from source.payload to target.payload;
    }
    interface def IF_IF_STA_036 {
        end source : PT_PT_STA_036;
        end target : ~PT_PT_STA_036;
        flow of I_ITM_STA_036 from source.payload to target.payload;
    }
}

package ProductDefinitions {
    private import ScalarValues::*;
    private import GeneralDefinitions::*;
    private import PortDefinitions::*;
    part def P_N_3111 {
        attribute productCode : String = "3111";
        attribute chineseName : String = "车轮";
        attribute level : Integer = 4;
        attribute parentCode : String = "3110";
        attribute role : String = "standard_299";
        attribute sourceType : String = "standard_299";
        attribute selected : Boolean = true;
        attribute leaf : Boolean = true;
        port rp_8ee7c79c0fe26b93 : PT_PT_PHY_006 {
            attribute sourcePortId : String = "PORT::3111::轮轨纵向机械作用端口::ITM-PHY-006::双向物理";
            attribute portName : String = "轮轨纵向机械作用端口";
            attribute direction : String = "双向物理";
            attribute activeStatus : Boolean = true;
        }
        port rp_f0350fc816a551ff : PT_PT_PHY_005 {
            attribute sourcePortId : String = "PORT::3111::轮轴旋转机械能端口::ITM-PHY-005::双向物理";
            attribute portName : String = "轮轴旋转机械能端口";
            attribute direction : String = "双向物理";
            attribute activeStatus : Boolean = true;
        }
    }
    part def P_N_3112 {
        attribute productCode : String = "3112";
        attribute chineseName : String = "车轴";
        attribute level : Integer = 4;
        attribute parentCode : String = "3110";
        attribute role : String = "standard_299";
        attribute sourceType : String = "standard_299";
        attribute selected : Boolean = true;
        attribute leaf : Boolean = true;
        port rp_6917242b1f7fc50f : PT_PT_PHY_005 {
            attribute sourcePortId : String = "PORT::3112::传动段旋转机械能端口::ITM-PHY-005::双向物理";
            attribute portName : String = "传动段旋转机械能端口";
            attribute direction : String = "双向物理";
            attribute activeStatus : Boolean = true;
        }
        port rp_c530418a51140052 : PT_PT_PHY_005 {
            attribute sourcePortId : String = "PORT::3112::轮对段旋转机械能端口::ITM-PHY-005::双向物理";
            attribute portName : String = "轮对段旋转机械能端口";
            attribute direction : String = "双向物理";
            attribute activeStatus : Boolean = true;
        }
    }
    part def P_N_3121 {
        attribute productCode : String = "3121";
        attribute chineseName : String = "齿轮箱主体";
        attribute level : Integer = 4;
        attribute parentCode : String = "3120";
        attribute role : String = "standard_299";
        attribute sourceType : String = "standard_299";
        attribute selected : Boolean = true;
        attribute leaf : Boolean = true;
        port rp_6464b6253314b208 : PT_PT_PHY_005 {
            attribute sourcePortId : String = "PORT::3121::低速轴旋转机械能端口::ITM-PHY-005::双向物理";
            attribute portName : String = "低速轴旋转机械能端口";
            attribute direction : String = "双向物理";
            attribute activeStatus : Boolean = true;
        }
        port rp_fdcd27ee9b0a936f : PT_PT_PHY_005 {
            attribute sourcePortId : String = "PORT::3121::高速轴旋转机械能端口::ITM-PHY-005::双向物理";
            attribute portName : String = "高速轴旋转机械能端口";
            attribute direction : String = "双向物理";
            attribute activeStatus : Boolean = true;
        }
    }
    part def P_N_3131 {
        attribute productCode : String = "3131";
        attribute chineseName : String = "外轮盘";
        attribute level : Integer = 4;
        attribute parentCode : String = "3130";
        attribute role : String = "standard_299";
        attribute sourceType : String = "standard_299";
        attribute selected : Boolean = true;
        attribute leaf : Boolean = true;
        port rp_06d152ddc255f2eb : PT_PT_PHY_007 {
            attribute sourcePortId : String = "PORT::3131::摩擦制动机械作用端口::ITM-PHY-007::双向物理";
            attribute portName : String = "摩擦制动机械作用端口";
            attribute direction : String = "双向物理";
            attribute activeStatus : Boolean = true;
        }
        port rp_ec78c2de89f1a17c : PT_PT_PHY_013 {
            attribute sourcePortId : String = "PORT::3131::热能_热流端口::ITM-PHY-013::双向物理";
            attribute portName : String = "热能/热流端口";
            attribute direction : String = "双向物理";
            attribute activeStatus : Boolean = true;
        }
    }
    part def P_N_3132 {
        attribute productCode : String = "3132";
        attribute chineseName : String = "内轮盘";
        attribute level : Integer = 4;
        attribute parentCode : String = "3130";
        attribute role : String = "standard_299";
        attribute sourceType : String = "standard_299";
        attribute selected : Boolean = true;
        attribute leaf : Boolean = true;
        port rp_6dfc099101cb436c : PT_PT_PHY_007 {
            attribute sourcePortId : String = "PORT::3132::摩擦制动机械作用端口::ITM-PHY-007::双向物理";
            attribute portName : String = "摩擦制动机械作用端口";
            attribute direction : String = "双向物理";
            attribute activeStatus : Boolean = true;
        }
        port rp_6069e8d0fbf298c5 : PT_PT_PHY_013 {
            attribute sourcePortId : String = "PORT::3132::热能_热流端口::ITM-PHY-013::双向物理";
            attribute portName : String = "热能/热流端口";
            attribute direction : String = "双向物理";
            attribute activeStatus : Boolean = true;
        }
    }
    part def P_N_3133 {
        attribute productCode : String = "3133";
        attribute chineseName : String = "轴盘";
        attribute level : Integer = 4;
        attribute parentCode : String = "3130";
        attribute role : String = "standard_299";
        attribute sourceType : String = "standard_299";
        attribute selected : Boolean = true;
        attribute leaf : Boolean = true;
        port rp_7738143ff23b3321 : PT_PT_PHY_007 {
            attribute sourcePortId : String = "PORT::3133::摩擦制动机械作用端口::ITM-PHY-007::双向物理";
            attribute portName : String = "摩擦制动机械作用端口";
            attribute direction : String = "双向物理";
            attribute activeStatus : Boolean = true;
        }
        port rp_24fa6cb520a8e2e2 : PT_PT_PHY_013 {
            attribute sourcePortId : String = "PORT::3133::热能_热流端口::ITM-PHY-013::双向物理";
            attribute portName : String = "热能/热流端口";
            attribute direction : String = "双向物理";
            attribute activeStatus : Boolean = true;
        }
    }
    part def P_N_3511 {
        attribute productCode : String = "3511";
        attribute chineseName : String = "联轴节(电机侧)";
        attribute level : Integer = 4;
        attribute parentCode : String = "3510";
        attribute role : String = "standard_299";
        attribute sourceType : String = "standard_299";
        attribute selected : Boolean = true;
        attribute leaf : Boolean = true;
        port rp_aa7691c6f81e4771 : PT_PT_PHY_005 {
            attribute sourcePortId : String = "PORT::3511::第一连接面旋转机械能端口::ITM-PHY-005::双向物理";
            attribute portName : String = "第一连接面旋转机械能端口";
            attribute direction : String = "双向物理";
            attribute activeStatus : Boolean = true;
        }
        port rp_813a305545723d57 : PT_PT_PHY_005 {
            attribute sourcePortId : String = "PORT::3511::第二连接面旋转机械能端口::ITM-PHY-005::双向物理";
            attribute portName : String = "第二连接面旋转机械能端口";
            attribute direction : String = "双向物理";
            attribute activeStatus : Boolean = true;
        }
    }
    part def P_N_3512 {
        attribute productCode : String = "3512";
        attribute chineseName : String = "联轴节(齿轮箱侧)";
        attribute level : Integer = 4;
        attribute parentCode : String = "3510";
        attribute role : String = "standard_299";
        attribute sourceType : String = "standard_299";
        attribute selected : Boolean = true;
        attribute leaf : Boolean = true;
        port rp_970ef7da9f850ce1 : PT_PT_PHY_005 {
            attribute sourcePortId : String = "PORT::3512::第一连接面旋转机械能端口::ITM-PHY-005::双向物理";
            attribute portName : String = "第一连接面旋转机械能端口";
            attribute direction : String = "双向物理";
            attribute activeStatus : Boolean = true;
        }
        port rp_c455741f6ca5a597 : PT_PT_PHY_005 {
            attribute sourcePortId : String = "PORT::3512::第二连接面旋转机械能端口::ITM-PHY-005::双向物理";
            attribute portName : String = "第二连接面旋转机械能端口";
            attribute direction : String = "双向物理";
            attribute activeStatus : Boolean = true;
        }
    }
    part def P_N_3514 {
        attribute productCode : String = "3514";
        attribute chineseName : String = "万向轴";
        attribute level : Integer = 4;
        attribute parentCode : String = "3510";
        attribute role : String = "standard_299";
        attribute sourceType : String = "standard_299";
        attribute selected : Boolean = true;
        attribute leaf : Boolean = true;
        port rp_b12dc4cc17618821 : PT_PT_PHY_005 {
            attribute sourcePortId : String = "PORT::3514::第一轴端旋转机械能端口::ITM-PHY-005::双向物理";
            attribute portName : String = "第一轴端旋转机械能端口";
            attribute direction : String = "双向物理";
            attribute activeStatus : Boolean = true;
        }
        port rp_4569aa8f56963dc6 : PT_PT_PHY_005 {
            attribute sourcePortId : String = "PORT::3514::第二轴端旋转机械能端口::ITM-PHY-005::双向物理";
            attribute portName : String = "第二轴端旋转机械能端口";
            attribute direction : String = "双向物理";
            attribute activeStatus : Boolean = true;
        }
    }
    part def P_N_3641 {
        attribute productCode : String = "3641";
        attribute chineseName : String = "轴端速度传感器";
        attribute level : Integer = 4;
        attribute parentCode : String = "3640";
        attribute role : String = "standard_299";
        attribute sourceType : String = "standard_299";
        attribute selected : Boolean = true;
        attribute leaf : Boolean = true;
        port rp_4ddc6037e5eea6fc : PT_PT_PHY_005 {
            attribute sourcePortId : String = "PORT::3641::旋转机械能端口::ITM-PHY-005::双向物理";
            attribute portName : String = "旋转机械能端口";
            attribute direction : String = "双向物理";
            attribute activeStatus : Boolean = true;
        }
        port rp_0875fbdf10c0dc7e : PT_PT_MEA_002 {
            attribute sourcePortId : String = "PORT::3641::轴端角速度输出::ITM-MEA-002::输出";
            attribute portName : String = "轴端角速度输出";
            attribute direction : String = "输出";
            attribute activeStatus : Boolean = true;
        }
    }
    part def P_N_3643 {
        attribute productCode : String = "3643";
        attribute chineseName : String = "齿轮箱速度传感器";
        attribute level : Integer = 4;
        attribute parentCode : String = "3640";
        attribute role : String = "standard_299";
        attribute sourceType : String = "standard_299";
        attribute selected : Boolean = true;
        attribute leaf : Boolean = true;
        port rp_48ddc723a7d58137 : PT_PT_PHY_005 {
            attribute sourcePortId : String = "PORT::3643::旋转机械能端口::ITM-PHY-005::双向物理";
            attribute portName : String = "旋转机械能端口";
            attribute direction : String = "双向物理";
            attribute activeStatus : Boolean = true;
        }
        port rp_213dbf9f44535a8a : PT_PT_MEA_003 {
            attribute sourcePortId : String = "PORT::3643::齿轮箱转速输出::ITM-MEA-003::输出";
            attribute portName : String = "齿轮箱转速输出";
            attribute direction : String = "输出";
            attribute activeStatus : Boolean = true;
        }
    }
    part def P_N_3644 {
        attribute productCode : String = "3644";
        attribute chineseName : String = "牵引电机速度传感器";
        attribute level : Integer = 4;
        attribute parentCode : String = "3640";
        attribute role : String = "standard_299";
        attribute sourceType : String = "standard_299";
        attribute selected : Boolean = true;
        attribute leaf : Boolean = true;
        port rp_af1c1b2c65382775 : PT_PT_PHY_005 {
            attribute sourcePortId : String = "PORT::3644::旋转机械能端口::ITM-PHY-005::双向物理";
            attribute portName : String = "旋转机械能端口";
            attribute direction : String = "双向物理";
            attribute activeStatus : Boolean = true;
        }
        port rp_08c271db56ce8427 : PT_PT_MEA_004 {
            attribute sourcePortId : String = "PORT::3644::牵引电机转速输出::ITM-MEA-004::输出";
            attribute portName : String = "牵引电机转速输出";
            attribute direction : String = "输出";
            attribute activeStatus : Boolean = true;
        }
    }
    part def P_N_3811 {
        attribute productCode : String = "3811";
        attribute chineseName : String = "撒砂控制单元";
        attribute level : Integer = 4;
        attribute parentCode : String = "3810";
        attribute role : String = "standard_299";
        attribute sourceType : String = "standard_299";
        attribute selected : Boolean = true;
        attribute leaf : Boolean = true;
        port rp_ad36be2404e763eb : PT_PT_PHY_015 {
            attribute sourcePortId : String = "PORT::3811::低压控制电能端口::ITM-PHY-015::双向物理";
            attribute portName : String = "低压控制电能端口";
            attribute direction : String = "双向物理";
            attribute activeStatus : Boolean = true;
        }
        port rp_3a8ce42fcde5acd8 : PT_PT_CMD_032 {
            attribute sourcePortId : String = "PORT::3811::撒砂执行指令输出::ITM-CMD-032::输出";
            attribute portName : String = "撒砂执行指令输出";
            attribute direction : String = "输出";
            attribute activeStatus : Boolean = true;
        }
        port rp_aa4dbc7721f19e23 : PT_PT_STA_012 {
            attribute sourcePortId : String = "PORT::3811::撒砂状态输出::ITM-STA-012::输出";
            attribute portName : String = "撒砂状态输出";
            attribute direction : String = "输出";
            attribute activeStatus : Boolean = true;
        }
        port rp_81d4e1a7092e0653 : ~PT_PT_CMD_024 {
            attribute sourcePortId : String = "PORT::3811::撒砂请求输入::ITM-CMD-024::输入";
            attribute portName : String = "撒砂请求输入";
            attribute direction : String = "输入";
            attribute activeStatus : Boolean = true;
        }
    }
    part def P_N_3813 {
        attribute productCode : String = "3813";
        attribute chineseName : String = "撒砂阀板组件";
        attribute level : Integer = 4;
        attribute parentCode : String = "3810";
        attribute role : String = "standard_299";
        attribute sourceType : String = "standard_299";
        attribute selected : Boolean = true;
        attribute leaf : Boolean = true;
        port rp_3f7e961856b812d2 : PT_PT_PHY_008 {
            attribute sourcePortId : String = "PORT::3813::主风压缩空气端口::ITM-PHY-008::双向物理";
            attribute portName : String = "主风压缩空气端口";
            attribute direction : String = "双向物理";
            attribute activeStatus : Boolean = true;
        }
        port rp_d951497aaa9989f0 : ~PT_PT_CMD_032 {
            attribute sourcePortId : String = "PORT::3813::撒砂执行指令输入::ITM-CMD-032::输入";
            attribute portName : String = "撒砂执行指令输入";
            attribute direction : String = "输入";
            attribute activeStatus : Boolean = true;
        }
        port rp_3344f097f2d78315 : PT_PT_STA_012 {
            attribute sourcePortId : String = "PORT::3813::撒砂状态输出::ITM-STA-012::输出";
            attribute portName : String = "撒砂状态输出";
            attribute direction : String = "输出";
            attribute activeStatus : Boolean = true;
        }
        port rp_c843e562c7ec3ed9 : PT_PT_PHY_012 {
            attribute sourcePortId : String = "PORT::3813::砂流端口::ITM-PHY-012::双向物理";
            attribute portName : String = "砂流端口";
            attribute direction : String = "双向物理";
            attribute activeStatus : Boolean = true;
        }
    }
    part def P_N_3814 {
        attribute productCode : String = "3814";
        attribute chineseName : String = "撒砂喷嘴组件";
        attribute level : Integer = 4;
        attribute parentCode : String = "3810";
        attribute role : String = "standard_299";
        attribute sourceType : String = "standard_299";
        attribute selected : Boolean = true;
        attribute leaf : Boolean = true;
        port rp_43d42f25a744fe07 : PT_PT_PHY_012 {
            attribute sourcePortId : String = "PORT::3814::砂流端口::ITM-PHY-012::双向物理";
            attribute portName : String = "砂流端口";
            attribute direction : String = "双向物理";
            attribute activeStatus : Boolean = true;
        }
    }
    part def P_N_4111 {
        attribute productCode : String = "4111";
        attribute chineseName : String = "碳滑板";
        attribute level : Integer = 4;
        attribute parentCode : String = "4110";
        attribute role : String = "standard_299";
        attribute sourceType : String = "standard_299";
        attribute selected : Boolean = true;
        attribute leaf : Boolean = true;
        port rp_ca65ceda639dfc7a : PT_PT_PHY_001 {
            attribute sourcePortId : String = "PORT::4111::导流端高压交流电能端口::ITM-PHY-001::双向物理";
            attribute portName : String = "导流端高压交流电能端口";
            attribute direction : String = "双向物理";
            attribute activeStatus : Boolean = true;
        }
        port rp_695b20573c740008 : PT_PT_PHY_001 {
            attribute sourcePortId : String = "PORT::4111::接触面高压交流电能端口::ITM-PHY-001::双向物理";
            attribute portName : String = "接触面高压交流电能端口";
            attribute direction : String = "双向物理";
            attribute activeStatus : Boolean = true;
        }
    }
    part def P_N_411C {
        attribute productCode : String = "411C";
        attribute chineseName : String = "受电弓电子控制单元";
        attribute level : Integer = 4;
        attribute parentCode : String = "4110";
        attribute role : String = "standard_299";
        attribute sourceType : String = "standard_299";
        attribute selected : Boolean = true;
        attribute leaf : Boolean = true;
        port rp_d6a2171160c4b693 : PT_PT_PHY_015 {
            attribute sourcePortId : String = "PORT::411C::低压控制电能端口::ITM-PHY-015::双向物理";
            attribute portName : String = "低压控制电能端口";
            attribute direction : String = "双向物理";
            attribute activeStatus : Boolean = true;
        }
        port rp_201c13a158f19a88 : ~PT_PT_CMD_018 {
            attribute sourcePortId : String = "PORT::411C::受电弓控制指令输入::ITM-CMD-018::输入";
            attribute portName : String = "受电弓控制指令输入";
            attribute direction : String = "输入";
            attribute activeStatus : Boolean = true;
        }
        port rp_72d2eed2608e1b56 : PT_PT_STA_015 {
            attribute sourcePortId : String = "PORT::411C::受电弓状态输出::ITM-STA-015::输出";
            attribute portName : String = "受电弓状态输出";
            attribute direction : String = "输出";
            attribute activeStatus : Boolean = true;
        }
        port rp_7f443c4ab63f77d2 : PT_PT_STA_016 {
            attribute sourcePortId : String = "PORT::411C::高压系统故障状态输出::ITM-STA-016::输出";
            attribute portName : String = "高压系统故障状态输出";
            attribute direction : String = "输出";
            attribute activeStatus : Boolean = true;
        }
    }
    part def P_N_4121 {
        attribute productCode : String = "4121";
        attribute chineseName : String = "受流器";
        attribute level : Integer = 4;
        attribute parentCode : String = "4120";
        attribute role : String = "standard_299";
        attribute sourceType : String = "standard_299";
        attribute selected : Boolean = true;
        attribute leaf : Boolean = true;
        port rp_d35e3f96846f95a6 : PT_PT_PHY_002 {
            attribute sourcePortId : String = "PORT::4121::受流端直流牵引供电电能端口::ITM-PHY-002::双向物理";
            attribute portName : String = "受流端直流牵引供电电能端口";
            attribute direction : String = "双向物理";
            attribute activeStatus : Boolean = false;
        }
        port rp_3a0861f1892e9d5f : PT_PT_PHY_002 {
            attribute sourcePortId : String = "PORT::4121::导流端直流牵引供电电能端口::ITM-PHY-002::双向物理";
            attribute portName : String = "导流端直流牵引供电电能端口";
            attribute direction : String = "双向物理";
            attribute activeStatus : Boolean = false;
        }
    }
    part def P_N_4211 {
        attribute productCode : String = "4211";
        attribute chineseName : String = "真空断路器";
        attribute level : Integer = 4;
        attribute parentCode : String = "4210";
        attribute role : String = "standard_299";
        attribute sourceType : String = "standard_299";
        attribute selected : Boolean = true;
        attribute leaf : Boolean = true;
        port rp_ee92cd728b152a90 : PT_PT_PHY_001 {
            attribute sourcePortId : String = "PORT::4211::出线侧高压交流电能端口::ITM-PHY-001::双向物理";
            attribute portName : String = "出线侧高压交流电能端口";
            attribute direction : String = "双向物理";
            attribute activeStatus : Boolean = true;
        }
        port rp_bba7ece236be8f3c : PT_PT_PHY_001 {
            attribute sourcePortId : String = "PORT::4211::进线侧高压交流电能端口::ITM-PHY-001::双向物理";
            attribute portName : String = "进线侧高压交流电能端口";
            attribute direction : String = "双向物理";
            attribute activeStatus : Boolean = true;
        }
        port rp_17bc6a2a377dffab : ~PT_PT_CMD_016 {
            attribute sourcePortId : String = "PORT::4211::高压断路器指令输入::ITM-CMD-016::输入";
            attribute portName : String = "高压断路器指令输入";
            attribute direction : String = "输入";
            attribute activeStatus : Boolean = true;
        }
        port rp_5301bf8bda8fba16 : PT_PT_STA_013 {
            attribute sourcePortId : String = "PORT::4211::高压断路器状态输出::ITM-STA-013::输出";
            attribute portName : String = "高压断路器状态输出";
            attribute direction : String = "输出";
            attribute activeStatus : Boolean = true;
        }
        port rp_5fec968d70e06b36 : PT_PT_STA_016 {
            attribute sourcePortId : String = "PORT::4211::高压系统故障状态输出::ITM-STA-016::输出";
            attribute portName : String = "高压系统故障状态输出";
            attribute direction : String = "输出";
            attribute activeStatus : Boolean = true;
        }
    }
    part def P_N_4212 {
        attribute productCode : String = "4212";
        attribute chineseName : String = "非真空隔离开关";
        attribute level : Integer = 4;
        attribute parentCode : String = "4210";
        attribute role : String = "standard_299";
        attribute sourceType : String = "standard_299";
        attribute selected : Boolean = true;
        attribute leaf : Boolean = true;
        port rp_0ce11b1eb6ca7ee8 : PT_PT_PHY_002 {
            attribute sourcePortId : String = "PORT::4212::出线侧直流牵引供电电能端口::ITM-PHY-002::双向物理";
            attribute portName : String = "出线侧直流牵引供电电能端口";
            attribute direction : String = "双向物理";
            attribute activeStatus : Boolean = false;
        }
        port rp_e1689d643b97d378 : PT_PT_PHY_001 {
            attribute sourcePortId : String = "PORT::4212::出线侧高压交流电能端口::ITM-PHY-001::双向物理";
            attribute portName : String = "出线侧高压交流电能端口";
            attribute direction : String = "双向物理";
            attribute activeStatus : Boolean = true;
        }
        port rp_e344333f6e011283 : PT_PT_PHY_002 {
            attribute sourcePortId : String = "PORT::4212::进线侧直流牵引供电电能端口::ITM-PHY-002::双向物理";
            attribute portName : String = "进线侧直流牵引供电电能端口";
            attribute direction : String = "双向物理";
            attribute activeStatus : Boolean = false;
        }
        port rp_4b65d610848833a3 : PT_PT_PHY_001 {
            attribute sourcePortId : String = "PORT::4212::进线侧高压交流电能端口::ITM-PHY-001::双向物理";
            attribute portName : String = "进线侧高压交流电能端口";
            attribute direction : String = "双向物理";
            attribute activeStatus : Boolean = true;
        }
        port rp_a29d16c43fc8d044 : ~PT_PT_CMD_017 {
            attribute sourcePortId : String = "PORT::4212::高压隔离开关指令输入::ITM-CMD-017::输入";
            attribute portName : String = "高压隔离开关指令输入";
            attribute direction : String = "输入";
            attribute activeStatus : Boolean = true;
        }
        port rp_62a902ccb2d5edf3 : PT_PT_STA_014 {
            attribute sourcePortId : String = "PORT::4212::高压隔离开关状态输出::ITM-STA-014::输出";
            attribute portName : String = "高压隔离开关状态输出";
            attribute direction : String = "输出";
            attribute activeStatus : Boolean = true;
        }
    }
    part def P_N_4235 {
        attribute productCode : String = "4235";
        attribute chineseName : String = "高压电压互感器";
        attribute level : Integer = 4;
        attribute parentCode : String = "4230";
        attribute role : String = "standard_299";
        attribute sourceType : String = "standard_299";
        attribute selected : Boolean = true;
        attribute leaf : Boolean = true;
        port rp_3e2b71c6b8d79136 : PT_PT_PHY_001 {
            attribute sourcePortId : String = "PORT::4235::高压交流电能端口::ITM-PHY-001::双向物理";
            attribute portName : String = "高压交流电能端口";
            attribute direction : String = "双向物理";
            attribute activeStatus : Boolean = true;
        }
        port rp_6fea4b377f978aac : PT_PT_MEA_005 {
            attribute sourcePortId : String = "PORT::4235::高压线路电压输出::ITM-MEA-005::输出";
            attribute portName : String = "高压线路电压输出";
            attribute direction : String = "输出";
            attribute activeStatus : Boolean = true;
        }
    }
    part def P_N_4236 {
        attribute productCode : String = "4236";
        attribute chineseName : String = "高压电流互感器";
        attribute level : Integer = 4;
        attribute parentCode : String = "4230";
        attribute role : String = "standard_299";
        attribute sourceType : String = "standard_299";
        attribute selected : Boolean = true;
        attribute leaf : Boolean = true;
        port rp_bb6f3fee449fd865 : PT_PT_PHY_001 {
            attribute sourcePortId : String = "PORT::4236::第一测量端高压交流电能端口::ITM-PHY-001::双向物理";
            attribute portName : String = "第一测量端高压交流电能端口";
            attribute direction : String = "双向物理";
            attribute activeStatus : Boolean = true;
        }
        port rp_78e99abb7d77c156 : PT_PT_PHY_001 {
            attribute sourcePortId : String = "PORT::4236::第二测量端高压交流电能端口::ITM-PHY-001::双向物理";
            attribute portName : String = "第二测量端高压交流电能端口";
            attribute direction : String = "双向物理";
            attribute activeStatus : Boolean = true;
        }
        port rp_9107465175683792 : PT_PT_MEA_006 {
            attribute sourcePortId : String = "PORT::4236::高压线路电流输出::ITM-MEA-006::输出";
            attribute portName : String = "高压线路电流输出";
            attribute direction : String = "输出";
            attribute activeStatus : Boolean = true;
        }
    }
    part def P_N_4238 {
        attribute productCode : String = "4238";
        attribute chineseName : String = "高压控制输入输出单元";
        attribute level : Integer = 4;
        attribute parentCode : String = "4230";
        attribute role : String = "standard_299";
        attribute sourceType : String = "standard_299";
        attribute selected : Boolean = true;
        attribute leaf : Boolean = true;
        port rp_dc173bda6489186d : PT_PT_PHY_015 {
            attribute sourcePortId : String = "PORT::4238::低压控制电能端口::ITM-PHY-015::双向物理";
            attribute portName : String = "低压控制电能端口";
            attribute direction : String = "双向物理";
            attribute activeStatus : Boolean = true;
        }
        port rp_71811e4b68798212 : ~PT_PT_CMD_018 {
            attribute sourcePortId : String = "PORT::4238::受电弓控制指令输入::ITM-CMD-018::输入";
            attribute portName : String = "受电弓控制指令输入";
            attribute direction : String = "输入";
            attribute activeStatus : Boolean = true;
        }
        port rp_9744a4b3a255a6e8 : PT_PT_CMD_018 {
            attribute sourcePortId : String = "PORT::4238::受电弓控制指令输出::ITM-CMD-018::输出";
            attribute portName : String = "受电弓控制指令输出";
            attribute direction : String = "输出";
            attribute activeStatus : Boolean = true;
        }
        port rp_d9d25dfbac32d1e3 : ~PT_PT_STA_015 {
            attribute sourcePortId : String = "PORT::4238::受电弓状态输入::ITM-STA-015::输入";
            attribute portName : String = "受电弓状态输入";
            attribute direction : String = "输入";
            attribute activeStatus : Boolean = true;
        }
        port rp_86fe03530d5b3c05 : PT_PT_STA_015 {
            attribute sourcePortId : String = "PORT::4238::受电弓状态输出::ITM-STA-015::输出";
            attribute portName : String = "受电弓状态输出";
            attribute direction : String = "输出";
            attribute activeStatus : Boolean = true;
        }
        port rp_d6b968957e3167c7 : ~PT_PT_CMD_016 {
            attribute sourcePortId : String = "PORT::4238::高压断路器指令输入::ITM-CMD-016::输入";
            attribute portName : String = "高压断路器指令输入";
            attribute direction : String = "输入";
            attribute activeStatus : Boolean = true;
        }
        port rp_65aacc4600de3990 : PT_PT_CMD_016 {
            attribute sourcePortId : String = "PORT::4238::高压断路器指令输出::ITM-CMD-016::输出";
            attribute portName : String = "高压断路器指令输出";
            attribute direction : String = "输出";
            attribute activeStatus : Boolean = true;
        }
        port rp_b26de8005dff4962 : ~PT_PT_STA_013 {
            attribute sourcePortId : String = "PORT::4238::高压断路器状态输入::ITM-STA-013::输入";
            attribute portName : String = "高压断路器状态输入";
            attribute direction : String = "输入";
            attribute activeStatus : Boolean = true;
        }
        port rp_0674d2b80a6a72da : PT_PT_STA_013 {
            attribute sourcePortId : String = "PORT::4238::高压断路器状态输出::ITM-STA-013::输出";
            attribute portName : String = "高压断路器状态输出";
            attribute direction : String = "输出";
            attribute activeStatus : Boolean = true;
        }
        port rp_11b7e7965ec2e386 : ~PT_PT_STA_016 {
            attribute sourcePortId : String = "PORT::4238::高压系统故障状态输入::ITM-STA-016::输入";
            attribute portName : String = "高压系统故障状态输入";
            attribute direction : String = "输入";
            attribute activeStatus : Boolean = true;
        }
        port rp_9458944450b0dd4c : PT_PT_STA_016 {
            attribute sourcePortId : String = "PORT::4238::高压系统故障状态输出::ITM-STA-016::输出";
            attribute portName : String = "高压系统故障状态输出";
            attribute direction : String = "输出";
            attribute activeStatus : Boolean = true;
        }
        port rp_c88ddcdfe3b55c9e : ~PT_PT_MEA_005 {
            attribute sourcePortId : String = "PORT::4238::高压线路电压输入::ITM-MEA-005::输入";
            attribute portName : String = "高压线路电压输入";
            attribute direction : String = "输入";
            attribute activeStatus : Boolean = true;
        }
        port rp_5576b5e0dbb912ba : PT_PT_MEA_005 {
            attribute sourcePortId : String = "PORT::4238::高压线路电压输出::ITM-MEA-005::输出";
            attribute portName : String = "高压线路电压输出";
            attribute direction : String = "输出";
            attribute activeStatus : Boolean = true;
        }
        port rp_afb7b0997d28e7cb : ~PT_PT_MEA_006 {
            attribute sourcePortId : String = "PORT::4238::高压线路电流输入::ITM-MEA-006::输入";
            attribute portName : String = "高压线路电流输入";
            attribute direction : String = "输入";
            attribute activeStatus : Boolean = true;
        }
        port rp_c7dcc306b020116f : PT_PT_MEA_006 {
            attribute sourcePortId : String = "PORT::4238::高压线路电流输出::ITM-MEA-006::输出";
            attribute portName : String = "高压线路电流输出";
            attribute direction : String = "输出";
            attribute activeStatus : Boolean = true;
        }
        port rp_f6362be8ea9a501f : ~PT_PT_CMD_017 {
            attribute sourcePortId : String = "PORT::4238::高压隔离开关指令输入::ITM-CMD-017::输入";
            attribute portName : String = "高压隔离开关指令输入";
            attribute direction : String = "输入";
            attribute activeStatus : Boolean = true;
        }
        port rp_ed1efa73e618c52f : PT_PT_CMD_017 {
            attribute sourcePortId : String = "PORT::4238::高压隔离开关指令输出::ITM-CMD-017::输出";
            attribute portName : String = "高压隔离开关指令输出";
            attribute direction : String = "输出";
            attribute activeStatus : Boolean = true;
        }
        port rp_b46091b51fbac2ba : ~PT_PT_STA_014 {
            attribute sourcePortId : String = "PORT::4238::高压隔离开关状态输入::ITM-STA-014::输入";
            attribute portName : String = "高压隔离开关状态输入";
            attribute direction : String = "输入";
            attribute activeStatus : Boolean = true;
        }
        port rp_7fe2b8fd826583f2 : PT_PT_STA_014 {
            attribute sourcePortId : String = "PORT::4238::高压隔离开关状态输出::ITM-STA-014::输出";
            attribute portName : String = "高压隔离开关状态输出";
            attribute direction : String = "输出";
            attribute activeStatus : Boolean = true;
        }
    }
    part def P_N_4239 {
        attribute productCode : String = "4239";
        attribute chineseName : String = "高压控制单元";
        attribute level : Integer = 4;
        attribute parentCode : String = "4230";
        attribute role : String = "standard_299";
        attribute sourceType : String = "standard_299";
        attribute selected : Boolean = true;
        attribute leaf : Boolean = true;
        port rp_9c4bbbf0c73d853e : PT_PT_PHY_015 {
            attribute sourcePortId : String = "PORT::4239::低压控制电能端口::ITM-PHY-015::双向物理";
            attribute portName : String = "低压控制电能端口";
            attribute direction : String = "双向物理";
            attribute activeStatus : Boolean = true;
        }
        port rp_327ede77d6565c4b : PT_PT_CMD_018 {
            attribute sourcePortId : String = "PORT::4239::受电弓控制指令输出::ITM-CMD-018::输出";
            attribute portName : String = "受电弓控制指令输出";
            attribute direction : String = "输出";
            attribute activeStatus : Boolean = true;
        }
        port rp_f3be8ead57323593 : ~PT_PT_STA_015 {
            attribute sourcePortId : String = "PORT::4239::受电弓状态输入::ITM-STA-015::输入";
            attribute portName : String = "受电弓状态输入";
            attribute direction : String = "输入";
            attribute activeStatus : Boolean = true;
        }
        port rp_a59e6c38c7d9e2cb : ~PT_PT_MEA_007 {
            attribute sourcePortId : String = "PORT::4239::线路频率输入::ITM-MEA-007::输入";
            attribute portName : String = "线路频率输入";
            attribute direction : String = "输入";
            attribute activeStatus : Boolean = true;
        }
        port rp_c9c4c887a8c7b2f0 : ~PT_PT_STA_024 {
            attribute sourcePortId : String = "PORT::4239::高压安全回路状态输入::ITM-STA-024::输入";
            attribute portName : String = "高压安全回路状态输入";
            attribute direction : String = "输入";
            attribute activeStatus : Boolean = true;
        }
        port rp_e67f315619e85b76 : PT_PT_CMD_016 {
            attribute sourcePortId : String = "PORT::4239::高压断路器指令输出::ITM-CMD-016::输出";
            attribute portName : String = "高压断路器指令输出";
            attribute direction : String = "输出";
            attribute activeStatus : Boolean = true;
        }
        port rp_1fd23591362c1d8d : ~PT_PT_STA_013 {
            attribute sourcePortId : String = "PORT::4239::高压断路器状态输入::ITM-STA-013::输入";
            attribute portName : String = "高压断路器状态输入";
            attribute direction : String = "输入";
            attribute activeStatus : Boolean = true;
        }
        port rp_390a7ebf7324c6d6 : PT_PT_STA_016 {
            attribute sourcePortId : String = "PORT::4239::高压系统故障状态汇总输出::ITM-STA-016::输出";
            attribute portName : String = "高压系统故障状态汇总输出";
            attribute direction : String = "输出";
            attribute activeStatus : Boolean = true;
        }
        port rp_be1480d12bc9092c : ~PT_PT_STA_016 {
            attribute sourcePortId : String = "PORT::4239::高压系统故障状态采集输入::ITM-STA-016::输入";
            attribute portName : String = "高压系统故障状态采集输入";
            attribute direction : String = "输入";
            attribute activeStatus : Boolean = true;
        }
        port rp_2802b0f2f54a548a : ~PT_PT_MEA_005 {
            attribute sourcePortId : String = "PORT::4239::高压线路电压输入::ITM-MEA-005::输入";
            attribute portName : String = "高压线路电压输入";
            attribute direction : String = "输入";
            attribute activeStatus : Boolean = true;
        }
        port rp_1a7ff383166e59f0 : ~PT_PT_MEA_006 {
            attribute sourcePortId : String = "PORT::4239::高压线路电流输入::ITM-MEA-006::输入";
            attribute portName : String = "高压线路电流输入";
            attribute direction : String = "输入";
            attribute activeStatus : Boolean = true;
        }
        port rp_e30c550b4d4e8d52 : PT_PT_CMD_017 {
            attribute sourcePortId : String = "PORT::4239::高压隔离开关指令输出::ITM-CMD-017::输出";
            attribute portName : String = "高压隔离开关指令输出";
            attribute direction : String = "输出";
            attribute activeStatus : Boolean = true;
        }
        port rp_30bf7d79603b941d : ~PT_PT_STA_014 {
            attribute sourcePortId : String = "PORT::4239::高压隔离开关状态输入::ITM-STA-014::输入";
            attribute portName : String = "高压隔离开关状态输入";
            attribute direction : String = "输入";
            attribute activeStatus : Boolean = true;
        }
    }
    part def P_N_4241 {
        attribute productCode : String = "4241";
        attribute chineseName : String = "处理单元";
        attribute level : Integer = 4;
        attribute parentCode : String = "4240";
        attribute role : String = "standard_299";
        attribute sourceType : String = "standard_299";
        attribute selected : Boolean = true;
        attribute leaf : Boolean = true;
        port rp_efc0e0ead5465ae4 : PT_PT_PHY_015 {
            attribute sourcePortId : String = "PORT::4241::低压控制电能端口::ITM-PHY-015::双向物理";
            attribute portName : String = "低压控制电能端口";
            attribute direction : String = "双向物理";
            attribute activeStatus : Boolean = true;
        }
        port rp_efaba262d19c325f : PT_PT_ACC_003 {
            attribute sourcePortId : String = "PORT::4241::回馈电网功率输出::ITM-ACC-003::输出";
            attribute portName : String = "回馈电网功率输出";
            attribute direction : String = "输出";
            attribute activeStatus : Boolean = true;
        }
        port rp_14501c1527ffc885 : PT_PT_ACC_009 {
            attribute sourcePortId : String = "PORT::4241::回馈电网累计能量输出::ITM-ACC-009::输出";
            attribute portName : String = "回馈电网累计能量输出";
            attribute direction : String = "输出";
            attribute activeStatus : Boolean = true;
        }
        port rp_c0f06cc787fcafcb : PT_PT_ACC_001 {
            attribute sourcePortId : String = "PORT::4241::牵引实际功率输出::ITM-ACC-001::输出";
            attribute portName : String = "牵引实际功率输出";
            attribute direction : String = "输出";
            attribute activeStatus : Boolean = true;
        }
        port rp_110b5a4be355bd73 : PT_PT_ACC_007 {
            attribute sourcePortId : String = "PORT::4241::牵引累计能量输出::ITM-ACC-007::输出";
            attribute portName : String = "牵引累计能量输出";
            attribute direction : String = "输出";
            attribute activeStatus : Boolean = true;
        }
        port rp_93eb42e9bb89d9ec : PT_PT_STA_035 {
            attribute sourcePortId : String = "PORT::4241::能量计量有效状态输出::ITM-STA-035::输出";
            attribute portName : String = "能量计量有效状态输出";
            attribute direction : String = "输出";
            attribute activeStatus : Boolean = true;
        }
        port rp_2b7dd272027fdc0b : ~PT_PT_MEA_005 {
            attribute sourcePortId : String = "PORT::4241::高压线路电压输入::ITM-MEA-005::输入";
            attribute portName : String = "高压线路电压输入";
            attribute direction : String = "输入";
            attribute activeStatus : Boolean = true;
        }
        port rp_f81c0f4a108acec4 : ~PT_PT_MEA_006 {
            attribute sourcePortId : String = "PORT::4241::高压线路电流输入::ITM-MEA-006::输入";
            attribute portName : String = "高压线路电流输入";
            attribute direction : String = "输入";
            attribute activeStatus : Boolean = true;
        }
    }
    part def P_N_4411 {
        attribute productCode : String = "4411";
        attribute chineseName : String = "接地变压器";
        attribute level : Integer = 4;
        attribute parentCode : String = "4410";
        attribute role : String = "standard_299";
        attribute sourceType : String = "standard_299";
        attribute selected : Boolean = true;
        attribute leaf : Boolean = true;
        port rp_45b0eaf9bb476ccf : PT_PT_PHY_011 {
            attribute sourcePortId : String = "PORT::4411::主回路侧回流电流端口::ITM-PHY-011::双向物理";
            attribute portName : String = "主回路侧回流电流端口";
            attribute direction : String = "双向物理";
            attribute activeStatus : Boolean = true;
        }
        port rp_5e63cd1bffa78a41 : PT_PT_PHY_011 {
            attribute sourcePortId : String = "PORT::4411::回流侧电流端口::ITM-PHY-011::双向物理";
            attribute portName : String = "回流侧电流端口";
            attribute direction : String = "双向物理";
            attribute activeStatus : Boolean = true;
        }
        port rp_c61d1b462f69be85 : PT_PT_PHY_013 {
            attribute sourcePortId : String = "PORT::4411::热能_热流端口::ITM-PHY-013::双向物理";
            attribute portName : String = "热能/热流端口";
            attribute direction : String = "双向物理";
            attribute activeStatus : Boolean = true;
        }
    }
    part def P_N_4412 {
        attribute productCode : String = "4412";
        attribute chineseName : String = "主回路接地电阻";
        attribute level : Integer = 4;
        attribute parentCode : String = "4410";
        attribute role : String = "standard_299";
        attribute sourceType : String = "standard_299";
        attribute selected : Boolean = true;
        attribute leaf : Boolean = true;
        port rp_e2c805a6993ee3dc : PT_PT_PHY_011 {
            attribute sourcePortId : String = "PORT::4412::主回路侧回流电流端口::ITM-PHY-011::双向物理";
            attribute portName : String = "主回路侧回流电流端口";
            attribute direction : String = "双向物理";
            attribute activeStatus : Boolean = true;
        }
        port rp_f330d9bb72a522df : PT_PT_PHY_011 {
            attribute sourcePortId : String = "PORT::4412::回流侧电流端口::ITM-PHY-011::双向物理";
            attribute portName : String = "回流侧电流端口";
            attribute direction : String = "双向物理";
            attribute activeStatus : Boolean = true;
        }
        port rp_b031f017471c85ee : PT_PT_PHY_013 {
            attribute sourcePortId : String = "PORT::4412::热能_热流端口::ITM-PHY-013::双向物理";
            attribute portName : String = "热能/热流端口";
            attribute direction : String = "双向物理";
            attribute activeStatus : Boolean = true;
        }
    }
    part def P_N_4413 {
        attribute productCode : String = "4413";
        attribute chineseName : String = "回流碳刷";
        attribute level : Integer = 4;
        attribute parentCode : String = "4410";
        attribute role : String = "standard_299";
        attribute sourceType : String = "standard_299";
        attribute selected : Boolean = true;
        attribute leaf : Boolean = true;
        port rp_cb582bd13ed15889 : PT_PT_PHY_011 {
            attribute sourcePortId : String = "PORT::4413::固定端回流电流端口::ITM-PHY-011::双向物理";
            attribute portName : String = "固定端回流电流端口";
            attribute direction : String = "双向物理";
            attribute activeStatus : Boolean = true;
        }
        port rp_c808ea5883784df8 : PT_PT_PHY_011 {
            attribute sourcePortId : String = "PORT::4413::旋转端回流电流端口::ITM-PHY-011::双向物理";
            attribute portName : String = "旋转端回流电流端口";
            attribute direction : String = "双向物理";
            attribute activeStatus : Boolean = true;
        }
    }
    part def P_N_4511 {
        attribute productCode : String = "4511";
        attribute chineseName : String = "主变压器主体";
        attribute level : Integer = 4;
        attribute parentCode : String = "4510";
        attribute role : String = "standard_299";
        attribute sourceType : String = "standard_299";
        attribute selected : Boolean = true;
        attribute leaf : Boolean = true;
        port rp_a6f93ee77144741e : PT_PT_PHY_014 {
            attribute sourcePortId : String = "PORT::4511::牵引变压器次级交流电能端口::ITM-PHY-014::双向物理";
            attribute portName : String = "牵引变压器次级交流电能端口";
            attribute direction : String = "双向物理";
            attribute activeStatus : Boolean = true;
        }
        port rp_c782fb362436088e : PT_PT_PHY_001 {
            attribute sourcePortId : String = "PORT::4511::高压交流电能端口::ITM-PHY-001::双向物理";
            attribute portName : String = "高压交流电能端口";
            attribute direction : String = "双向物理";
            attribute activeStatus : Boolean = true;
        }
    }
    part def P_N_4513 {
        attribute productCode : String = "4513";
        attribute chineseName : String = "电抗器";
        attribute level : Integer = 4;
        attribute parentCode : String = "4510";
        attribute role : String = "standard_299";
        attribute sourceType : String = "standard_299";
        attribute selected : Boolean = true;
        attribute leaf : Boolean = true;
        port rp_88e2bd038f100aa3 : PT_PT_PHY_014 {
            attribute sourcePortId : String = "PORT::4513::第一交流电能端口::ITM-PHY-014::双向物理";
            attribute portName : String = "第一交流电能端口";
            attribute direction : String = "双向物理";
            attribute activeStatus : Boolean = true;
        }
        port rp_f597e9dc63931270 : PT_PT_PHY_014 {
            attribute sourcePortId : String = "PORT::4513::第二交流电能端口::ITM-PHY-014::双向物理";
            attribute portName : String = "第二交流电能端口";
            attribute direction : String = "双向物理";
            attribute activeStatus : Boolean = true;
        }
    }
    part def P_N_4517 {
        attribute productCode : String = "4517";
        attribute chineseName : String = "主变压器检测及保护元件";
        attribute level : Integer = 4;
        attribute parentCode : String = "4510";
        attribute role : String = "standard_299";
        attribute sourceType : String = "standard_299";
        attribute selected : Boolean = true;
        attribute leaf : Boolean = true;
        port rp_b094956bc66dfaad : PT_PT_MEA_022 {
            attribute sourcePortId : String = "PORT::4517::主变压器温度输出::ITM-MEA-022::输出";
            attribute portName : String = "主变压器温度输出";
            attribute direction : String = "输出";
            attribute activeStatus : Boolean = true;
        }
        port rp_fa22ceafa52cda89 : PT_PT_PHY_015 {
            attribute sourcePortId : String = "PORT::4517::低压控制电能端口::ITM-PHY-015::双向物理";
            attribute portName : String = "低压控制电能端口";
            attribute direction : String = "双向物理";
            attribute activeStatus : Boolean = true;
        }
        port rp_b93b1716e8b4e844 : PT_PT_STA_016 {
            attribute sourcePortId : String = "PORT::4517::高压系统故障状态输出::ITM-STA-016::输出";
            attribute portName : String = "高压系统故障状态输出";
            attribute direction : String = "输出";
            attribute activeStatus : Boolean = true;
        }
    }
    part def P_N_4518 {
        attribute productCode : String = "4518";
        attribute chineseName : String = "主变压器控制装置";
        attribute level : Integer = 4;
        attribute parentCode : String = "4510";
        attribute role : String = "standard_299";
        attribute sourceType : String = "standard_299";
        attribute selected : Boolean = true;
        attribute leaf : Boolean = true;
        port rp_f46b3d97e0fceb9e : ~PT_PT_MEA_022 {
            attribute sourcePortId : String = "PORT::4518::主变压器温度输入::ITM-MEA-022::输入";
            attribute portName : String = "主变压器温度输入";
            attribute direction : String = "输入";
            attribute activeStatus : Boolean = true;
        }
        port rp_950aee7777f5ea28 : PT_PT_PHY_015 {
            attribute sourcePortId : String = "PORT::4518::低压控制电能端口::ITM-PHY-015::双向物理";
            attribute portName : String = "低压控制电能端口";
            attribute direction : String = "双向物理";
            attribute activeStatus : Boolean = true;
        }
        port rp_c08bc1e5a0818e4a : PT_PT_CMD_016 {
            attribute sourcePortId : String = "PORT::4518::高压断路器指令输出::ITM-CMD-016::输出";
            attribute portName : String = "高压断路器指令输出";
            attribute direction : String = "输出";
            attribute activeStatus : Boolean = true;
        }
        port rp_67eef246e016ac82 : ~PT_PT_STA_013 {
            attribute sourcePortId : String = "PORT::4518::高压断路器状态输入::ITM-STA-013::输入";
            attribute portName : String = "高压断路器状态输入";
            attribute direction : String = "输入";
            attribute activeStatus : Boolean = true;
        }
        port rp_a87c9390595138d6 : ~PT_PT_STA_016 {
            attribute sourcePortId : String = "PORT::4518::高压系统故障状态输入::ITM-STA-016::输入";
            attribute portName : String = "高压系统故障状态输入";
            attribute direction : String = "输入";
            attribute activeStatus : Boolean = true;
        }
    }
    part def P_N_5111 {
        attribute productCode : String = "5111";
        attribute chineseName : String = "网侧变流器控制模块";
        attribute level : Integer = 4;
        attribute parentCode : String = "5110";
        attribute role : String = "standard_299";
        attribute sourceType : String = "standard_299";
        attribute selected : Boolean = true;
        attribute leaf : Boolean = true;
        port rp_a9ddcab662f35564 : ~PT_PT_MEA_008 {
            attribute sourcePortId : String = "PORT::5111::中间直流母线电压输入::ITM-MEA-008::输入";
            attribute portName : String = "中间直流母线电压输入";
            attribute direction : String = "输入";
            attribute activeStatus : Boolean = true;
        }
        port rp_0e00d1e837346b81 : ~PT_PT_MEA_009 {
            attribute sourcePortId : String = "PORT::5111::中间直流母线电流输入::ITM-MEA-009::输入";
            attribute portName : String = "中间直流母线电流输入";
            attribute direction : String = "输入";
            attribute activeStatus : Boolean = true;
        }
        port rp_9ceb0295e403e673 : PT_PT_PHY_015 {
            attribute sourcePortId : String = "PORT::5111::低压控制电能端口::ITM-PHY-015::双向物理";
            attribute portName : String = "低压控制电能端口";
            attribute direction : String = "双向物理";
            attribute activeStatus : Boolean = true;
        }
        port rp_6076ccac9d0762b3 : PT_PT_LIM_004 {
            attribute sourcePortId : String = "PORT::5111::再生功率上限输出::ITM-LIM-004::输出";
            attribute portName : String = "再生功率上限输出";
            attribute direction : String = "输出";
            attribute activeStatus : Boolean = true;
        }
        port rp_cd7720cf9a4eae22 : PT_PT_LIM_005 {
            attribute sourcePortId : String = "PORT::5111::接触网可接收功率输出::ITM-LIM-005::输出";
            attribute portName : String = "接触网可接收功率输出";
            attribute direction : String = "输出";
            attribute activeStatus : Boolean = true;
        }
        port rp_f5af02c6a1f2ad2c : PT_PT_STA_019 {
            attribute sourcePortId : String = "PORT::5111::牵引变流器故障状态输出::ITM-STA-019::输出";
            attribute portName : String = "牵引变流器故障状态输出";
            attribute direction : String = "输出";
            attribute activeStatus : Boolean = true;
        }
        port rp_c8b770c2e6dd3117 : ~PT_PT_MEA_007 {
            attribute sourcePortId : String = "PORT::5111::线路频率输入::ITM-MEA-007::输入";
            attribute portName : String = "线路频率输入";
            attribute direction : String = "输入";
            attribute activeStatus : Boolean = true;
        }
        port rp_4963dcfde3fa1724 : PT_PT_STA_017 {
            attribute sourcePortId : String = "PORT::5111::网侧变流器状态输出::ITM-STA-017::输出";
            attribute portName : String = "网侧变流器状态输出";
            attribute direction : String = "输出";
            attribute activeStatus : Boolean = true;
        }
        port rp_3c696476f82c2ae5 : PT_PT_CMD_010 {
            attribute sourcePortId : String = "PORT::5111::网侧变流控制指令输出::ITM-CMD-010::输出";
            attribute portName : String = "网侧变流控制指令输出";
            attribute direction : String = "输出";
            attribute activeStatus : Boolean = true;
        }
        port rp_5f90d6dd8fba4321 : ~PT_PT_MEA_005 {
            attribute sourcePortId : String = "PORT::5111::高压线路电压输入::ITM-MEA-005::输入";
            attribute portName : String = "高压线路电压输入";
            attribute direction : String = "输入";
            attribute activeStatus : Boolean = true;
        }
        port rp_651700e69b7dccba : ~PT_PT_MEA_006 {
            attribute sourcePortId : String = "PORT::5111::高压线路电流输入::ITM-MEA-006::输入";
            attribute portName : String = "高压线路电流输入";
            attribute direction : String = "输入";
            attribute activeStatus : Boolean = true;
        }
    }
    part def P_N_5112 {
        attribute productCode : String = "5112";
        attribute chineseName : String = "电机侧变流器控制模块";
        attribute level : Integer = 4;
        attribute parentCode : String = "5110";
        attribute role : String = "standard_299";
        attribute sourceType : String = "standard_299";
        attribute selected : Boolean = true;
        attribute leaf : Boolean = true;
        port rp_69252f780afe77e0 : ~PT_PT_MEA_008 {
            attribute sourcePortId : String = "PORT::5112::中间直流母线电压输入::ITM-MEA-008::输入";
            attribute portName : String = "中间直流母线电压输入";
            attribute direction : String = "输入";
            attribute activeStatus : Boolean = true;
        }
        port rp_6ad9df7ab3c91425 : ~PT_PT_MEA_009 {
            attribute sourcePortId : String = "PORT::5112::中间直流母线电流输入::ITM-MEA-009::输入";
            attribute portName : String = "中间直流母线电流输入";
            attribute direction : String = "输入";
            attribute activeStatus : Boolean = true;
        }
        port rp_c60f875ac7e265d0 : PT_PT_PHY_015 {
            attribute sourcePortId : String = "PORT::5112::低压控制电能端口::ITM-PHY-015::双向物理";
            attribute portName : String = "低压控制电能端口";
            attribute direction : String = "双向物理";
            attribute activeStatus : Boolean = true;
        }
        port rp_4bfdb59776ff813f : PT_PT_LIM_004 {
            attribute sourcePortId : String = "PORT::5112::再生功率上限输出::ITM-LIM-004::输出";
            attribute portName : String = "再生功率上限输出";
            attribute direction : String = "输出";
            attribute activeStatus : Boolean = true;
        }
        port rp_f2ec293da4f6084c : PT_PT_STA_002 {
            attribute sourcePortId : String = "PORT::5112::动态制动可用状态输出::ITM-STA-002::输出";
            attribute portName : String = "动态制动可用状态输出";
            attribute direction : String = "输出";
            attribute activeStatus : Boolean = true;
        }
        port rp_b88bbe834e3c6412 : PT_PT_LIM_001 {
            attribute sourcePortId : String = "PORT::5112::可用动态制动力输出::ITM-LIM-001::输出";
            attribute portName : String = "可用动态制动力输出";
            attribute direction : String = "输出";
            attribute activeStatus : Boolean = true;
        }
        port rp_13733b4e36d92f10 : PT_PT_LIM_003 {
            attribute sourcePortId : String = "PORT::5112::牵引_再生转矩上限输出::ITM-LIM-003::输出";
            attribute portName : String = "牵引/再生转矩上限输出";
            attribute direction : String = "输出";
            attribute activeStatus : Boolean = true;
        }
        port rp_32a86e4500c85071 : PT_PT_STA_019 {
            attribute sourcePortId : String = "PORT::5112::牵引变流器故障状态输出::ITM-STA-019::输出";
            attribute portName : String = "牵引变流器故障状态输出";
            attribute direction : String = "输出";
            attribute activeStatus : Boolean = true;
        }
        port rp_5337e32cd07bb034 : PT_PT_STA_001 {
            attribute sourcePortId : String = "PORT::5112::牵引可用状态输出::ITM-STA-001::输出";
            attribute portName : String = "牵引可用状态输出";
            attribute direction : String = "输出";
            attribute activeStatus : Boolean = true;
        }
        port rp_4557e9b0656c46f5 : ~PT_PT_MEA_012 {
            attribute sourcePortId : String = "PORT::5112::牵引电机实际转矩输入::ITM-MEA-012::输入";
            attribute portName : String = "牵引电机实际转矩输入";
            attribute direction : String = "输入";
            attribute activeStatus : Boolean = true;
        }
        port rp_6ce5fb5c81d47ab4 : ~PT_PT_CMD_012 {
            attribute sourcePortId : String = "PORT::5112::牵引电机转矩请求输入::ITM-CMD-012::输入";
            attribute portName : String = "牵引电机转矩请求输入";
            attribute direction : String = "输入";
            attribute activeStatus : Boolean = true;
        }
        port rp_780596fabcc73a0f : ~PT_PT_MEA_004 {
            attribute sourcePortId : String = "PORT::5112::牵引电机转速输入::ITM-MEA-004::输入";
            attribute portName : String = "牵引电机转速输入";
            attribute direction : String = "输入";
            attribute activeStatus : Boolean = true;
        }
        port rp_f6a2c78620450314 : PT_PT_STA_018 {
            attribute sourcePortId : String = "PORT::5112::电机侧变流器状态输出::ITM-STA-018::输出";
            attribute portName : String = "电机侧变流器状态输出";
            attribute direction : String = "输出";
            attribute activeStatus : Boolean = true;
        }
        port rp_c98f6aa887541378 : PT_PT_CMD_011 {
            attribute sourcePortId : String = "PORT::5112::电机侧变流控制指令输出::ITM-CMD-011::输出";
            attribute portName : String = "电机侧变流控制指令输出";
            attribute direction : String = "输出";
            attribute activeStatus : Boolean = true;
        }
        port rp_21e86fb073b61523 : ~PT_PT_MEA_011 {
            attribute sourcePortId : String = "PORT::5112::电机侧相电压输入::ITM-MEA-011::输入";
            attribute portName : String = "电机侧相电压输入";
            attribute direction : String = "输入";
            attribute activeStatus : Boolean = true;
        }
        port rp_3db204c2f5a83c7f : ~PT_PT_MEA_010 {
            attribute sourcePortId : String = "PORT::5112::电机侧相电流输入::ITM-MEA-010::输入";
            attribute portName : String = "电机侧相电流输入";
            attribute direction : String = "输入";
            attribute activeStatus : Boolean = true;
        }
    }
    part def P_N_5113 {
        attribute productCode : String = "5113";
        attribute chineseName : String = "变流器检测保护组件";
        attribute level : Integer = 4;
        attribute parentCode : String = "5110";
        attribute role : String = "standard_299";
        attribute sourceType : String = "standard_299";
        attribute selected : Boolean = true;
        attribute leaf : Boolean = true;
        port rp_2af3dfa3c81ea109 : PT_PT_MEA_008 {
            attribute sourcePortId : String = "PORT::5113::中间直流母线电压输出::ITM-MEA-008::输出";
            attribute portName : String = "中间直流母线电压输出";
            attribute direction : String = "输出";
            attribute activeStatus : Boolean = true;
        }
        port rp_4e1f60c0e22c417d : PT_PT_MEA_009 {
            attribute sourcePortId : String = "PORT::5113::中间直流母线电流输出::ITM-MEA-009::输出";
            attribute portName : String = "中间直流母线电流输出";
            attribute direction : String = "输出";
            attribute activeStatus : Boolean = true;
        }
        port rp_7668c7c1973850f4 : PT_PT_STA_020 {
            attribute sourcePortId : String = "PORT::5113::中间直流环节保护状态输出::ITM-STA-020::输出";
            attribute portName : String = "中间直流环节保护状态输出";
            attribute direction : String = "输出";
            attribute activeStatus : Boolean = true;
        }
        port rp_6f5e3f6e1f0f9b1a : PT_PT_PHY_015 {
            attribute sourcePortId : String = "PORT::5113::低压控制电能端口::ITM-PHY-015::双向物理";
            attribute portName : String = "低压控制电能端口";
            attribute direction : String = "双向物理";
            attribute activeStatus : Boolean = true;
        }
        port rp_d93ff3dea2be11bd : PT_PT_STA_019 {
            attribute sourcePortId : String = "PORT::5113::牵引变流器故障状态输出::ITM-STA-019::输出";
            attribute portName : String = "牵引变流器故障状态输出";
            attribute direction : String = "输出";
            attribute activeStatus : Boolean = true;
        }
        port rp_a16fb7ddd6338cf7 : PT_PT_MEA_023 {
            attribute sourcePortId : String = "PORT::5113::牵引变流器温度输出::ITM-MEA-023::输出";
            attribute portName : String = "牵引变流器温度输出";
            attribute direction : String = "输出";
            attribute activeStatus : Boolean = true;
        }
        port rp_4be030fa7e242206 : PT_PT_MEA_010 {
            attribute sourcePortId : String = "PORT::5113::电机侧相电流输出::ITM-MEA-010::输出";
            attribute portName : String = "电机侧相电流输出";
            attribute direction : String = "输出";
            attribute activeStatus : Boolean = true;
        }
        port rp_d8b59663e8e8813a : PT_PT_LIM_007 {
            attribute sourcePortId : String = "PORT::5113::直流母线电压上限输出::ITM-LIM-007::输出";
            attribute portName : String = "直流母线电压上限输出";
            attribute direction : String = "输出";
            attribute activeStatus : Boolean = true;
        }
    }
    part def P_N_5121 {
        attribute productCode : String = "5121";
        attribute chineseName : String = "预充电组件";
        attribute level : Integer = 4;
        attribute parentCode : String = "5120";
        attribute role : String = "standard_299";
        attribute sourceType : String = "standard_299";
        attribute selected : Boolean = true;
        attribute leaf : Boolean = true;
        port rp_e5b052bb75ba8a31 : PT_PT_PHY_003 {
            attribute sourcePortId : String = "PORT::5121::中间直流电能端口::ITM-PHY-003::双向物理";
            attribute portName : String = "中间直流电能端口";
            attribute direction : String = "双向物理";
            attribute activeStatus : Boolean = true;
        }
        port rp_9dedfe88c8a34261 : PT_PT_PHY_014 {
            attribute sourcePortId : String = "PORT::5121::牵引变压器次级交流电能端口::ITM-PHY-014::双向物理";
            attribute portName : String = "牵引变压器次级交流电能端口";
            attribute direction : String = "双向物理";
            attribute activeStatus : Boolean = true;
        }
        port rp_809fd610416051c1 : PT_PT_PHY_002 {
            attribute sourcePortId : String = "PORT::5121::直流牵引供电电能端口::ITM-PHY-002::双向物理";
            attribute portName : String = "直流牵引供电电能端口";
            attribute direction : String = "双向物理";
            attribute activeStatus : Boolean = false;
        }
        port rp_56d2d83f54b98301 : ~PT_PT_CMD_013 {
            attribute sourcePortId : String = "PORT::5121::预充电指令输入::ITM-CMD-013::输入";
            attribute portName : String = "预充电指令输入";
            attribute direction : String = "输入";
            attribute activeStatus : Boolean = true;
        }
        port rp_923b8f78dd634c21 : PT_PT_STA_021 {
            attribute sourcePortId : String = "PORT::5121::预充电状态输出::ITM-STA-021::输出";
            attribute portName : String = "预充电状态输出";
            attribute direction : String = "输出";
            attribute activeStatus : Boolean = true;
        }
    }
    part def P_N_5122 {
        attribute productCode : String = "5122";
        attribute chineseName : String = "输入组件";
        attribute level : Integer = 4;
        attribute parentCode : String = "5120";
        attribute role : String = "standard_299";
        attribute sourceType : String = "standard_299";
        attribute selected : Boolean = true;
        attribute leaf : Boolean = true;
        port rp_6e156eb66bd95a75 : PT_PT_PHY_003 {
            attribute sourcePortId : String = "PORT::5122::中间直流电能端口::ITM-PHY-003::双向物理";
            attribute portName : String = "中间直流电能端口";
            attribute direction : String = "双向物理";
            attribute activeStatus : Boolean = true;
        }
        port rp_0b57347688ba1240 : PT_PT_PHY_014 {
            attribute sourcePortId : String = "PORT::5122::牵引变压器次级交流电能端口::ITM-PHY-014::双向物理";
            attribute portName : String = "牵引变压器次级交流电能端口";
            attribute direction : String = "双向物理";
            attribute activeStatus : Boolean = true;
        }
        port rp_32a63d8c830a3ed0 : ~PT_PT_CMD_014 {
            attribute sourcePortId : String = "PORT::5122::牵引输入接通指令输入::ITM-CMD-014::输入";
            attribute portName : String = "牵引输入接通指令输入";
            attribute direction : String = "输入";
            attribute activeStatus : Boolean = true;
        }
        port rp_a512199cf2d52036 : PT_PT_STA_022 {
            attribute sourcePortId : String = "PORT::5122::牵引输入接通状态输出::ITM-STA-022::输出";
            attribute portName : String = "牵引输入接通状态输出";
            attribute direction : String = "输出";
            attribute activeStatus : Boolean = true;
        }
        port rp_08aeac9ca9c693f3 : PT_PT_PHY_002 {
            attribute sourcePortId : String = "PORT::5122::直流牵引供电电能端口::ITM-PHY-002::双向物理";
            attribute portName : String = "直流牵引供电电能端口";
            attribute direction : String = "双向物理";
            attribute activeStatus : Boolean = false;
        }
    }
    part def P_N_5131 {
        attribute productCode : String = "5131";
        attribute chineseName : String = "网侧变流模块";
        attribute level : Integer = 4;
        attribute parentCode : String = "5130";
        attribute role : String = "standard_299";
        attribute sourceType : String = "standard_299";
        attribute selected : Boolean = true;
        attribute leaf : Boolean = true;
        port rp_58be8015ffe61769 : PT_PT_MEA_008 {
            attribute sourcePortId : String = "PORT::5131::中间直流母线电压输出::ITM-MEA-008::输出";
            attribute portName : String = "中间直流母线电压输出";
            attribute direction : String = "输出";
            attribute activeStatus : Boolean = true;
        }
        port rp_0772d9885daa45bb : PT_PT_MEA_009 {
            attribute sourcePortId : String = "PORT::5131::中间直流母线电流输出::ITM-MEA-009::输出";
            attribute portName : String = "中间直流母线电流输出";
            attribute direction : String = "输出";
            attribute activeStatus : Boolean = true;
        }
        port rp_f010ea68f7dddd01 : PT_PT_PHY_003 {
            attribute sourcePortId : String = "PORT::5131::中间直流电能端口::ITM-PHY-003::双向物理";
            attribute portName : String = "中间直流电能端口";
            attribute direction : String = "双向物理";
            attribute activeStatus : Boolean = true;
        }
        port rp_95979f7c6bb276e7 : PT_PT_ACC_003 {
            attribute sourcePortId : String = "PORT::5131::回馈电网功率输出::ITM-ACC-003::输出";
            attribute portName : String = "回馈电网功率输出";
            attribute direction : String = "输出";
            attribute activeStatus : Boolean = true;
        }
        port rp_32d77ca0c1d88b50 : PT_PT_PHY_014 {
            attribute sourcePortId : String = "PORT::5131::牵引变压器次级交流电能端口::ITM-PHY-014::双向物理";
            attribute portName : String = "牵引变压器次级交流电能端口";
            attribute direction : String = "双向物理";
            attribute activeStatus : Boolean = true;
        }
        port rp_c06b535bf90fa905 : ~PT_PT_CMD_010 {
            attribute sourcePortId : String = "PORT::5131::网侧变流控制指令输入::ITM-CMD-010::输入";
            attribute portName : String = "网侧变流控制指令输入";
            attribute direction : String = "输入";
            attribute activeStatus : Boolean = true;
        }
        port rp_3b17660257f9fac5 : PT_PT_MEA_005 {
            attribute sourcePortId : String = "PORT::5131::高压线路电压输出::ITM-MEA-005::输出";
            attribute portName : String = "高压线路电压输出";
            attribute direction : String = "输出";
            attribute activeStatus : Boolean = true;
        }
        port rp_5e454de063d535e5 : PT_PT_MEA_006 {
            attribute sourcePortId : String = "PORT::5131::高压线路电流输出::ITM-MEA-006::输出";
            attribute portName : String = "高压线路电流输出";
            attribute direction : String = "输出";
            attribute activeStatus : Boolean = true;
        }
    }
    part def P_N_5132 {
        attribute productCode : String = "5132";
        attribute chineseName : String = "电机侧变流模块";
        attribute level : Integer = 4;
        attribute parentCode : String = "5130";
        attribute role : String = "standard_299";
        attribute sourceType : String = "standard_299";
        attribute selected : Boolean = true;
        attribute leaf : Boolean = true;
        port rp_770f7e1c507cc073 : PT_PT_PHY_004 {
            attribute sourcePortId : String = "PORT::5132::三相交流电能端口::ITM-PHY-004::双向物理";
            attribute portName : String = "三相交流电能端口";
            attribute direction : String = "双向物理";
            attribute activeStatus : Boolean = true;
        }
        port rp_4fd822f2b574e9e6 : PT_PT_MEA_008 {
            attribute sourcePortId : String = "PORT::5132::中间直流母线电压输出::ITM-MEA-008::输出";
            attribute portName : String = "中间直流母线电压输出";
            attribute direction : String = "输出";
            attribute activeStatus : Boolean = true;
        }
        port rp_097124295bc446b2 : PT_PT_MEA_009 {
            attribute sourcePortId : String = "PORT::5132::中间直流母线电流输出::ITM-MEA-009::输出";
            attribute portName : String = "中间直流母线电流输出";
            attribute direction : String = "输出";
            attribute activeStatus : Boolean = true;
        }
        port rp_e9be022214796a74 : PT_PT_PHY_003 {
            attribute sourcePortId : String = "PORT::5132::中间直流电能端口::ITM-PHY-003::双向物理";
            attribute portName : String = "中间直流电能端口";
            attribute direction : String = "双向物理";
            attribute activeStatus : Boolean = true;
        }
        port rp_75d86c9dc39b94b8 : PT_PT_ACC_002 {
            attribute sourcePortId : String = "PORT::5132::实际再生功率输出::ITM-ACC-002::输出";
            attribute portName : String = "实际再生功率输出";
            attribute direction : String = "输出";
            attribute activeStatus : Boolean = true;
        }
        port rp_406d292901368d53 : ~PT_PT_CMD_011 {
            attribute sourcePortId : String = "PORT::5132::电机侧变流控制指令输入::ITM-CMD-011::输入";
            attribute portName : String = "电机侧变流控制指令输入";
            attribute direction : String = "输入";
            attribute activeStatus : Boolean = true;
        }
        port rp_22f4369ba0161f6e : PT_PT_MEA_011 {
            attribute sourcePortId : String = "PORT::5132::电机侧相电压输出::ITM-MEA-011::输出";
            attribute portName : String = "电机侧相电压输出";
            attribute direction : String = "输出";
            attribute activeStatus : Boolean = true;
        }
        port rp_7044b6667673db95 : PT_PT_MEA_010 {
            attribute sourcePortId : String = "PORT::5132::电机侧相电流输出::ITM-MEA-010::输出";
            attribute portName : String = "电机侧相电流输出";
            attribute direction : String = "输出";
            attribute activeStatus : Boolean = true;
        }
    }
    part def P_N_5133 {
        attribute productCode : String = "5133";
        attribute chineseName : String = "放电电阻控制模块";
        attribute level : Integer = 4;
        attribute parentCode : String = "5130";
        attribute role : String = "standard_299";
        attribute sourceType : String = "standard_299";
        attribute selected : Boolean = true;
        attribute leaf : Boolean = true;
        port rp_60d9996fadd55bff : ~PT_PT_MEA_008 {
            attribute sourcePortId : String = "PORT::5133::中间直流母线电压输入::ITM-MEA-008::输入";
            attribute portName : String = "中间直流母线电压输入";
            attribute direction : String = "输入";
            attribute activeStatus : Boolean = true;
        }
        port rp_b97ef71e558464ef : PT_PT_PHY_015 {
            attribute sourcePortId : String = "PORT::5133::低压控制电能端口::ITM-PHY-015::双向物理";
            attribute portName : String = "低压控制电能端口";
            attribute direction : String = "双向物理";
            attribute activeStatus : Boolean = true;
        }
        port rp_77ee52e55ac1ca4e : ~PT_PT_CMD_015 {
            attribute sourcePortId : String = "PORT::5133::制动斩波器指令输入::ITM-CMD-015::输入";
            attribute portName : String = "制动斩波器指令输入";
            attribute direction : String = "输入";
            attribute activeStatus : Boolean = true;
        }
        port rp_ceecb00c1539e058 : PT_PT_STA_023 {
            attribute sourcePortId : String = "PORT::5133::制动斩波器状态输出::ITM-STA-023::输出";
            attribute portName : String = "制动斩波器状态输出";
            attribute direction : String = "输出";
            attribute activeStatus : Boolean = true;
        }
        port rp_cb7199d5a5b150b9 : PT_PT_LIM_006 {
            attribute sourcePortId : String = "PORT::5133::制动电阻可耗散功率输出::ITM-LIM-006::输出";
            attribute portName : String = "制动电阻可耗散功率输出";
            attribute direction : String = "输出";
            attribute activeStatus : Boolean = true;
        }
    }
    part def P_N_5142 {
        attribute productCode : String = "5142";
        attribute chineseName : String = "放电电阻器";
        attribute level : Integer = 4;
        attribute parentCode : String = "5140";
        attribute role : String = "standard_299";
        attribute sourceType : String = "standard_299";
        attribute selected : Boolean = true;
        attribute leaf : Boolean = true;
        port rp_14fbc389883862a8 : PT_PT_PHY_003 {
            attribute sourcePortId : String = "PORT::5142::中间直流电能端口::ITM-PHY-003::双向物理";
            attribute portName : String = "中间直流电能端口";
            attribute direction : String = "双向物理";
            attribute activeStatus : Boolean = true;
        }
        port rp_2057e03c844b131c : PT_PT_MEA_024 {
            attribute sourcePortId : String = "PORT::5142::制动电阻温度输出::ITM-MEA-024::输出";
            attribute portName : String = "制动电阻温度输出";
            attribute direction : String = "输出";
            attribute activeStatus : Boolean = true;
        }
        port rp_ff09931c451e831b : PT_PT_ACC_005 {
            attribute sourcePortId : String = "PORT::5142::制动电阻耗散功率输出::ITM-ACC-005::输出";
            attribute portName : String = "制动电阻耗散功率输出";
            attribute direction : String = "输出";
            attribute activeStatus : Boolean = true;
        }
        port rp_876f0faee3baf027 : PT_PT_ACC_012 {
            attribute sourcePortId : String = "PORT::5142::制动电阻耗散累计能量输出::ITM-ACC-012::输出";
            attribute portName : String = "制动电阻耗散累计能量输出";
            attribute direction : String = "输出";
            attribute activeStatus : Boolean = true;
        }
        port rp_7c7ad9996d24b706 : PT_PT_PHY_013 {
            attribute sourcePortId : String = "PORT::5142::热能_热流端口::ITM-PHY-013::双向物理";
            attribute portName : String = "热能/热流端口";
            attribute direction : String = "双向物理";
            attribute activeStatus : Boolean = true;
        }
    }
    part def P_N_5145 {
        attribute productCode : String = "5145";
        attribute chineseName : String = "中间直流环节检测保护组件";
        attribute level : Integer = 4;
        attribute parentCode : String = "5140";
        attribute role : String = "standard_299";
        attribute sourceType : String = "standard_299";
        attribute selected : Boolean = true;
        attribute leaf : Boolean = true;
        port rp_1680714c67f7d311 : PT_PT_MEA_008 {
            attribute sourcePortId : String = "PORT::5145::中间直流母线电压输出::ITM-MEA-008::输出";
            attribute portName : String = "中间直流母线电压输出";
            attribute direction : String = "输出";
            attribute activeStatus : Boolean = true;
        }
        port rp_a9cc4822e30a5ede : PT_PT_MEA_009 {
            attribute sourcePortId : String = "PORT::5145::中间直流母线电流输出::ITM-MEA-009::输出";
            attribute portName : String = "中间直流母线电流输出";
            attribute direction : String = "输出";
            attribute activeStatus : Boolean = true;
        }
        port rp_0fe575c7a29bac8c : PT_PT_STA_020 {
            attribute sourcePortId : String = "PORT::5145::中间直流环节保护状态输出::ITM-STA-020::输出";
            attribute portName : String = "中间直流环节保护状态输出";
            attribute direction : String = "输出";
            attribute activeStatus : Boolean = true;
        }
        port rp_b22756bb5d4e9b69 : PT_PT_PHY_015 {
            attribute sourcePortId : String = "PORT::5145::低压控制电能端口::ITM-PHY-015::双向物理";
            attribute portName : String = "低压控制电能端口";
            attribute direction : String = "双向物理";
            attribute activeStatus : Boolean = true;
        }
        port rp_e58f80e07056f3fb : PT_PT_CMD_015 {
            attribute sourcePortId : String = "PORT::5145::制动斩波器指令输出::ITM-CMD-015::输出";
            attribute portName : String = "制动斩波器指令输出";
            attribute direction : String = "输出";
            attribute activeStatus : Boolean = true;
        }
        port rp_3c3f036735b04fe0 : PT_PT_LIM_007 {
            attribute sourcePortId : String = "PORT::5145::直流母线电压上限输出::ITM-LIM-007::输出";
            attribute portName : String = "直流母线电压上限输出";
            attribute direction : String = "输出";
            attribute activeStatus : Boolean = true;
        }
    }
    part def P_N_5311 {
        attribute productCode : String = "5311";
        attribute chineseName : String = "牵引电机";
        attribute level : Integer = 4;
        attribute parentCode : String = "5310";
        attribute role : String = "standard_299";
        attribute sourceType : String = "standard_299";
        attribute selected : Boolean = true;
        attribute leaf : Boolean = true;
        port rp_57f3c317ac0c860d : PT_PT_PHY_004 {
            attribute sourcePortId : String = "PORT::5311::三相交流电能端口::ITM-PHY-004::双向物理";
            attribute portName : String = "三相交流电能端口";
            attribute direction : String = "双向物理";
            attribute activeStatus : Boolean = true;
        }
        port rp_97eb613c06ae1b2e : PT_PT_PHY_005 {
            attribute sourcePortId : String = "PORT::5311::旋转机械能端口::ITM-PHY-005::双向物理";
            attribute portName : String = "旋转机械能端口";
            attribute direction : String = "双向物理";
            attribute activeStatus : Boolean = true;
        }
        port rp_10bb4c4f0063bc18 : PT_PT_MEA_012 {
            attribute sourcePortId : String = "PORT::5311::牵引电机实际转矩输出::ITM-MEA-012::输出";
            attribute portName : String = "牵引电机实际转矩输出";
            attribute direction : String = "输出";
            attribute activeStatus : Boolean = true;
        }
        port rp_79c695a1342df24f : PT_PT_MEA_004 {
            attribute sourcePortId : String = "PORT::5311::牵引电机转速输出::ITM-MEA-004::输出";
            attribute portName : String = "牵引电机转速输出";
            attribute direction : String = "输出";
            attribute activeStatus : Boolean = true;
        }
        port rp_537e9856bafa2a02 : PT_PT_MEA_011 {
            attribute sourcePortId : String = "PORT::5311::电机侧相电压输出::ITM-MEA-011::输出";
            attribute portName : String = "电机侧相电压输出";
            attribute direction : String = "输出";
            attribute activeStatus : Boolean = true;
        }
        port rp_147751bb1b62d40a : PT_PT_MEA_010 {
            attribute sourcePortId : String = "PORT::5311::电机侧相电流输出::ITM-MEA-010::输出";
            attribute portName : String = "电机侧相电流输出";
            attribute direction : String = "输出";
            attribute activeStatus : Boolean = true;
        }
    }
    part def P_N_7124 {
        attribute productCode : String = "7124";
        attribute chineseName : String = "制动风缸";
        attribute level : Integer = 4;
        attribute parentCode : String = "7120";
        attribute role : String = "standard_299";
        attribute sourceType : String = "standard_299";
        attribute selected : Boolean = true;
        attribute leaf : Boolean = true;
        port rp_732b5a3acb4e2be0 : PT_PT_PHY_008 {
            attribute sourcePortId : String = "PORT::7124::主风压缩空气端口::ITM-PHY-008::双向物理";
            attribute portName : String = "主风压缩空气端口";
            attribute direction : String = "双向物理";
            attribute activeStatus : Boolean = true;
        }
        port rp_d2f380834008b7d7 : PT_PT_MEA_015 {
            attribute sourcePortId : String = "PORT::7124::制动风缸压力输出::ITM-MEA-015::输出";
            attribute portName : String = "制动风缸压力输出";
            attribute direction : String = "输出";
            attribute activeStatus : Boolean = true;
        }
    }
    part def P_N_7131 {
        attribute productCode : String = "7131";
        attribute chineseName : String = "总风管";
        attribute level : Integer = 4;
        attribute parentCode : String = "7130";
        attribute role : String = "standard_299";
        attribute sourceType : String = "standard_299";
        attribute selected : Boolean = true;
        attribute leaf : Boolean = true;
        port rp_e275cbf47ef42c02 : PT_PT_PHY_008 {
            attribute sourcePortId : String = "PORT::7131::总风管末端压缩空气端口::ITM-PHY-008::双向物理";
            attribute portName : String = "总风管末端压缩空气端口";
            attribute direction : String = "双向物理";
            attribute activeStatus : Boolean = true;
        }
        port rp_e73ffca5021e0883 : PT_PT_PHY_008 {
            attribute sourcePortId : String = "PORT::7131::总风管首端压缩空气端口::ITM-PHY-008::双向物理";
            attribute portName : String = "总风管首端压缩空气端口";
            attribute direction : String = "双向物理";
            attribute activeStatus : Boolean = true;
        }
    }
    part def P_N_7142 {
        attribute productCode : String = "7142";
        attribute chineseName : String = "总风管压力传感器";
        attribute level : Integer = 4;
        attribute parentCode : String = "7140";
        attribute role : String = "standard_299";
        attribute sourceType : String = "standard_299";
        attribute selected : Boolean = true;
        attribute leaf : Boolean = true;
        port rp_b1c762907b90d07b : PT_PT_PHY_008 {
            attribute sourcePortId : String = "PORT::7142::主风压缩空气端口::ITM-PHY-008::双向物理";
            attribute portName : String = "主风压缩空气端口";
            attribute direction : String = "双向物理";
            attribute activeStatus : Boolean = true;
        }
        port rp_3909c089bc66e61b : PT_PT_STA_009 {
            attribute sourcePortId : String = "PORT::7142::低风压状态输出::ITM-STA-009::输出";
            attribute portName : String = "低风压状态输出";
            attribute direction : String = "输出";
            attribute activeStatus : Boolean = true;
        }
        port rp_52f3b82b80918b84 : PT_PT_MEA_014 {
            attribute sourcePortId : String = "PORT::7142::总风管压力输出::ITM-MEA-014::输出";
            attribute portName : String = "总风管压力输出";
            attribute direction : String = "输出";
            attribute activeStatus : Boolean = true;
        }
    }
    part def P_N_7211 {
        attribute productCode : String = "7211";
        attribute chineseName : String = "电子制动控制单元(EBCU)";
        attribute level : Integer = 4;
        attribute parentCode : String = "7210";
        attribute role : String = "standard_299";
        attribute sourceType : String = "standard_299";
        attribute selected : Boolean = true;
        attribute leaf : Boolean = true;
        port rp_b34d5a11f0a32260 : PT_PT_PHY_015 {
            attribute sourcePortId : String = "PORT::7211::低压控制电能端口::ITM-PHY-015::双向物理";
            attribute portName : String = "低压控制电能端口";
            attribute direction : String = "双向物理";
            attribute activeStatus : Boolean = true;
        }
        port rp_19f11c6ee3cbf055 : ~PT_PT_STA_009 {
            attribute sourcePortId : String = "PORT::7211::低风压状态输入::ITM-STA-009::输入";
            attribute portName : String = "低风压状态输入";
            attribute direction : String = "输入";
            attribute activeStatus : Boolean = true;
        }
        port rp_dc452be8b7368516 : ~PT_PT_MEA_018 {
            attribute sourcePortId : String = "PORT::7211::列车质量输入::ITM-MEA-018::输入";
            attribute portName : String = "列车质量输入";
            attribute direction : String = "输入";
            attribute activeStatus : Boolean = true;
        }
        port rp_e64f014311f04d50 : ~PT_PT_MEA_001 {
            attribute sourcePortId : String = "PORT::7211::列车速度输入::ITM-MEA-001::输入";
            attribute portName : String = "列车速度输入";
            attribute direction : String = "输入";
            attribute activeStatus : Boolean = true;
        }
        port rp_daaf414c1711f2bd : ~PT_PT_STA_025 {
            attribute sourcePortId : String = "PORT::7211::制动安全回路状态输入::ITM-STA-025::输入";
            attribute portName : String = "制动安全回路状态输入";
            attribute direction : String = "输入";
            attribute activeStatus : Boolean = true;
        }
        port rp_ab6bd1b4df7dcdff : PT_PT_STA_008 {
            attribute sourcePortId : String = "PORT::7211::制动拖滞状态输出::ITM-STA-008::输出";
            attribute portName : String = "制动拖滞状态输出";
            attribute direction : String = "输出";
            attribute activeStatus : Boolean = true;
        }
        port rp_0209c7a801f78e7e : PT_PT_CMD_031 {
            attribute sourcePortId : String = "PORT::7211::制动控制接触器指令输出::ITM-CMD-031::输出";
            attribute portName : String = "制动控制接触器指令输出";
            attribute direction : String = "输出";
            attribute activeStatus : Boolean = true;
        }
        port rp_15b87d372ae097d8 : PT_PT_STA_007 {
            attribute sourcePortId : String = "PORT::7211::制动控制故障状态输出::ITM-STA-007::输出";
            attribute portName : String = "制动控制故障状态输出";
            attribute direction : String = "输出";
            attribute activeStatus : Boolean = true;
        }
        port rp_77f0053899ab19da : PT_PT_STA_004 {
            attribute sourcePortId : String = "PORT::7211::制动施加状态输出::ITM-STA-004::输出";
            attribute portName : String = "制动施加状态输出";
            attribute direction : String = "输出";
            attribute activeStatus : Boolean = true;
        }
        port rp_c4074d88ed5949ec : PT_PT_CMD_022 {
            attribute sourcePortId : String = "PORT::7211::制动电磁阀指令输出::ITM-CMD-022::输出";
            attribute portName : String = "制动电磁阀指令输出";
            attribute direction : String = "输出";
            attribute activeStatus : Boolean = true;
        }
        port rp_c021f63639408eff : PT_PT_STA_003 {
            attribute sourcePortId : String = "PORT::7211::制动系统可用状态输出::ITM-STA-003::输出";
            attribute portName : String = "制动系统可用状态输出";
            attribute direction : String = "输出";
            attribute activeStatus : Boolean = true;
        }
        port rp_abc190a288d4c9d5 : PT_PT_CMD_019 {
            attribute sourcePortId : String = "PORT::7211::制动缓解指令输出::ITM-CMD-019::输出";
            attribute portName : String = "制动缓解指令输出";
            attribute direction : String = "输出";
            attribute activeStatus : Boolean = true;
        }
        port rp_ef5148faa6dc1c65 : PT_PT_STA_005 {
            attribute sourcePortId : String = "PORT::7211::制动缓解状态输出::ITM-STA-005::输出";
            attribute portName : String = "制动缓解状态输出";
            attribute direction : String = "输出";
            attribute activeStatus : Boolean = true;
        }
        port rp_f786158194c89c8a : ~PT_PT_MEA_016 {
            attribute sourcePortId : String = "PORT::7211::制动缸压力输入::ITM-MEA-016::输入";
            attribute portName : String = "制动缸压力输入";
            attribute direction : String = "输入";
            attribute activeStatus : Boolean = true;
        }
        port rp_a882b33038ce4623 : PT_PT_CMD_020 {
            attribute sourcePortId : String = "PORT::7211::制动隔离指令输出::ITM-CMD-020::输出";
            attribute portName : String = "制动隔离指令输出";
            attribute direction : String = "输出";
            attribute activeStatus : Boolean = true;
        }
        port rp_43e35aa64c833efc : PT_PT_STA_006 {
            attribute sourcePortId : String = "PORT::7211::制动隔离状态输出::ITM-STA-006::输出";
            attribute portName : String = "制动隔离状态输出";
            attribute direction : String = "输出";
            attribute activeStatus : Boolean = true;
        }
        port rp_0194ebfed505dfb5 : PT_PT_CMD_006 {
            attribute sourcePortId : String = "PORT::7211::动态制动力请求输出::ITM-CMD-006::输出";
            attribute portName : String = "动态制动力请求输出";
            attribute direction : String = "输出";
            attribute activeStatus : Boolean = true;
        }
        port rp_d26568a796272d7a : ~PT_PT_STA_002 {
            attribute sourcePortId : String = "PORT::7211::动态制动可用状态输入::ITM-STA-002::输入";
            attribute portName : String = "动态制动可用状态输入";
            attribute direction : String = "输入";
            attribute activeStatus : Boolean = true;
        }
        port rp_e4d6047a07b1416e : ~PT_PT_LIM_001 {
            attribute sourcePortId : String = "PORT::7211::可用动态制动力输入::ITM-LIM-001::输入";
            attribute portName : String = "可用动态制动力输入";
            attribute direction : String = "输入";
            attribute activeStatus : Boolean = true;
        }
        port rp_3e14ce961c10da8c : PT_PT_LIM_002 {
            attribute sourcePortId : String = "PORT::7211::可用摩擦制动力输出::ITM-LIM-002::输出";
            attribute portName : String = "可用摩擦制动力输出";
            attribute direction : String = "输出";
            attribute activeStatus : Boolean = true;
        }
        port rp_fbdca500826ff2e8 : ~PT_PT_MEA_021 {
            attribute sourcePortId : String = "PORT::7211::可用黏着系数估计输入::ITM-MEA-021::输入";
            attribute portName : String = "可用黏着系数估计输入";
            attribute direction : String = "输入";
            attribute activeStatus : Boolean = true;
        }
        port rp_5fc26e41f5b877b0 : ~PT_PT_LIM_008 {
            attribute sourcePortId : String = "PORT::7211::可用黏着限制输入::ITM-LIM-008::输入";
            attribute portName : String = "可用黏着限制输入";
            attribute direction : String = "输入";
            attribute activeStatus : Boolean = true;
        }
        port rp_da3049ae66223d22 : ~PT_PT_CMD_030 {
            attribute sourcePortId : String = "PORT::7211::安全停车_制动请求输入::ITM-CMD-030::输入";
            attribute portName : String = "安全停车/制动请求输入";
            attribute direction : String = "输入";
            attribute activeStatus : Boolean = true;
        }
        port rp_179bcc3fb8dacbbf : ~PT_PT_MEA_013 {
            attribute sourcePortId : String = "PORT::7211::实际动态制动力输入::ITM-MEA-013::输入";
            attribute portName : String = "实际动态制动力输入";
            attribute direction : String = "输入";
            attribute activeStatus : Boolean = true;
        }
        port rp_5b7be52aa5b6e9d0 : ~PT_PT_MEA_017 {
            attribute sourcePortId : String = "PORT::7211::实际摩擦制动力输入::ITM-MEA-017::输入";
            attribute portName : String = "实际摩擦制动力输入";
            attribute direction : String = "输入";
            attribute activeStatus : Boolean = true;
        }
        port rp_04cfaf63bfa3ed70 : ~PT_PT_MEA_014 {
            attribute sourcePortId : String = "PORT::7211::总风管压力输入::ITM-MEA-014::输入";
            attribute portName : String = "总风管压力输入";
            attribute direction : String = "输入";
            attribute activeStatus : Boolean = true;
        }
        port rp_45bcc846bb19f806 : PT_PT_CMD_007 {
            attribute sourcePortId : String = "PORT::7211::摩擦制动力请求输出::ITM-CMD-007::输出";
            attribute portName : String = "摩擦制动力请求输出";
            attribute direction : String = "输出";
            attribute activeStatus : Boolean = true;
        }
        port rp_a477083b284f478e : ~PT_PT_LIM_014 {
            attribute sourcePortId : String = "PORT::7211::最大允许减速度输入::ITM-LIM-014::输入";
            attribute portName : String = "最大允许减速度输入";
            attribute direction : String = "输入";
            attribute activeStatus : Boolean = true;
        }
        port rp_8f4a8ea2188f4411 : ~PT_PT_LIM_013 {
            attribute sourcePortId : String = "PORT::7211::最大允许制动力输入::ITM-LIM-013::输入";
            attribute portName : String = "最大允许制动力输入";
            attribute direction : String = "输入";
            attribute activeStatus : Boolean = true;
        }
        port rp_77afbfa330bfb95e : ~PT_PT_CMD_003 {
            attribute sourcePortId : String = "PORT::7211::服务制动请求输入::ITM-CMD-003::输入";
            attribute portName : String = "服务制动请求输入";
            attribute direction : String = "输入";
            attribute activeStatus : Boolean = true;
        }
        port rp_a53270fc181cff7c : PT_PT_CMD_008 {
            attribute sourcePortId : String = "PORT::7211::牵引切除请求输出::ITM-CMD-008::输出";
            attribute portName : String = "牵引切除请求输出";
            attribute direction : String = "输出";
            attribute activeStatus : Boolean = true;
        }
        port rp_dff51f26bbd38512 : PT_PT_CMD_021 {
            attribute sourcePortId : String = "PORT::7211::电空转换阀指令输出::ITM-CMD-021::输出";
            attribute portName : String = "电空转换阀指令输出";
            attribute direction : String = "输出";
            attribute activeStatus : Boolean = true;
        }
        port rp_faa6c7c9931b0a58 : ~PT_PT_CMD_004 {
            attribute sourcePortId : String = "PORT::7211::紧急制动请求输入::ITM-CMD-004::输入";
            attribute portName : String = "紧急制动请求输入";
            attribute direction : String = "输入";
            attribute activeStatus : Boolean = true;
        }
        port rp_ed944339b1333e10 : ~PT_PT_MEA_019 {
            attribute sourcePortId : String = "PORT::7211::车辆载荷系数输入::ITM-MEA-019::输入";
            attribute portName : String = "车辆载荷系数输入";
            attribute direction : String = "输入";
            attribute activeStatus : Boolean = true;
        }
        port rp_2885b328b968942b : ~PT_PT_MEA_020 {
            attribute sourcePortId : String = "PORT::7211::轮轨滑移率输入::ITM-MEA-020::输入";
            attribute portName : String = "轮轨滑移率输入";
            attribute direction : String = "输入";
            attribute activeStatus : Boolean = true;
        }
        port rp_91854864e6254d28 : PT_PT_CMD_023 {
            attribute sourcePortId : String = "PORT::7211::防滑干预指令输出::ITM-CMD-023::输出";
            attribute portName : String = "防滑干预指令输出";
            attribute direction : String = "输出";
            attribute activeStatus : Boolean = true;
        }
        port rp_574d2a0f495ec049 : PT_PT_STA_011 {
            attribute sourcePortId : String = "PORT::7211::防滑故障状态输出::ITM-STA-011::输出";
            attribute portName : String = "防滑故障状态输出";
            attribute direction : String = "输出";
            attribute activeStatus : Boolean = true;
        }
        port rp_e71bf6c6a81443a2 : PT_PT_STA_010 {
            attribute sourcePortId : String = "PORT::7211::防滑激活状态输出::ITM-STA-010::输出";
            attribute portName : String = "防滑激活状态输出";
            attribute direction : String = "输出";
            attribute activeStatus : Boolean = true;
        }
    }
    part def P_N_7213 {
        attribute productCode : String = "7213";
        attribute chineseName : String = "制动控制接触器及其他";
        attribute level : Integer = 4;
        attribute parentCode : String = "7210";
        attribute role : String = "standard_299";
        attribute sourceType : String = "standard_299";
        attribute selected : Boolean = true;
        attribute leaf : Boolean = true;
        port rp_de41681b082603dc : PT_PT_PHY_015 {
            attribute sourcePortId : String = "PORT::7213::低压控制电能端口::ITM-PHY-015::双向物理";
            attribute portName : String = "低压控制电能端口";
            attribute direction : String = "双向物理";
            attribute activeStatus : Boolean = true;
        }
        port rp_de845d22bfa40612 : ~PT_PT_CMD_031 {
            attribute sourcePortId : String = "PORT::7213::制动控制接触器指令输入::ITM-CMD-031::输入";
            attribute portName : String = "制动控制接触器指令输入";
            attribute direction : String = "输入";
            attribute activeStatus : Boolean = true;
        }
        port rp_a3e87ce99fd880b3 : PT_PT_STA_036 {
            attribute sourcePortId : String = "PORT::7213::制动控制接触器状态输出::ITM-STA-036::输出";
            attribute portName : String = "制动控制接触器状态输出";
            attribute direction : String = "输出";
            attribute activeStatus : Boolean = true;
        }
    }
    part def P_N_7222 {
        attribute productCode : String = "7222";
        attribute chineseName : String = "电空转换阀";
        attribute level : Integer = 4;
        attribute parentCode : String = "7220";
        attribute role : String = "standard_299";
        attribute sourceType : String = "standard_299";
        attribute selected : Boolean = true;
        attribute leaf : Boolean = true;
        port rp_d9d50ab5a08a26a5 : PT_PT_PHY_008 {
            attribute sourcePortId : String = "PORT::7222::主风压缩空气端口::ITM-PHY-008::双向物理";
            attribute portName : String = "主风压缩空气端口";
            attribute direction : String = "双向物理";
            attribute activeStatus : Boolean = true;
        }
        port rp_43816dbefe351165 : PT_PT_PHY_009 {
            attribute sourcePortId : String = "PORT::7222::制动控制压缩空气端口::ITM-PHY-009::双向物理";
            attribute portName : String = "制动控制压缩空气端口";
            attribute direction : String = "双向物理";
            attribute activeStatus : Boolean = true;
        }
        port rp_ddeea781987ee55c : ~PT_PT_CMD_021 {
            attribute sourcePortId : String = "PORT::7222::电空转换阀指令输入::ITM-CMD-021::输入";
            attribute portName : String = "电空转换阀指令输入";
            attribute direction : String = "输入";
            attribute activeStatus : Boolean = true;
        }
    }
    part def P_N_7223 {
        attribute productCode : String = "7223";
        attribute chineseName : String = "中继阀";
        attribute level : Integer = 4;
        attribute parentCode : String = "7220";
        attribute role : String = "standard_299";
        attribute sourceType : String = "standard_299";
        attribute selected : Boolean = true;
        attribute leaf : Boolean = true;
        port rp_4abc41bc202f61af : PT_PT_PHY_008 {
            attribute sourcePortId : String = "PORT::7223::主风压缩空气端口::ITM-PHY-008::双向物理";
            attribute portName : String = "主风压缩空气端口";
            attribute direction : String = "双向物理";
            attribute activeStatus : Boolean = true;
        }
        port rp_9441f85d6ac8b0ed : PT_PT_PHY_009 {
            attribute sourcePortId : String = "PORT::7223::制动控制压缩空气端口::ITM-PHY-009::双向物理";
            attribute portName : String = "制动控制压缩空气端口";
            attribute direction : String = "双向物理";
            attribute activeStatus : Boolean = true;
        }
        port rp_26b22e117179b62a : PT_PT_PHY_010 {
            attribute sourcePortId : String = "PORT::7223::制动缸压缩空气端口::ITM-PHY-010::双向物理";
            attribute portName : String = "制动缸压缩空气端口";
            attribute direction : String = "双向物理";
            attribute activeStatus : Boolean = true;
        }
    }
    part def P_N_7224 {
        attribute productCode : String = "7224";
        attribute chineseName : String = "空重车调整阀";
        attribute level : Integer = 4;
        attribute parentCode : String = "7220";
        attribute role : String = "standard_299";
        attribute sourceType : String = "standard_299";
        attribute selected : Boolean = true;
        attribute leaf : Boolean = true;
        port rp_291ee811748691f6 : PT_PT_PHY_008 {
            attribute sourcePortId : String = "PORT::7224::主风压缩空气端口::ITM-PHY-008::双向物理";
            attribute portName : String = "主风压缩空气端口";
            attribute direction : String = "双向物理";
            attribute activeStatus : Boolean = true;
        }
        port rp_0714bcd5930c027b : PT_PT_PHY_009 {
            attribute sourcePortId : String = "PORT::7224::制动控制压缩空气端口::ITM-PHY-009::双向物理";
            attribute portName : String = "制动控制压缩空气端口";
            attribute direction : String = "双向物理";
            attribute activeStatus : Boolean = true;
        }
        port rp_b9cbc1c18f711974 : ~PT_PT_MEA_019 {
            attribute sourcePortId : String = "PORT::7224::车辆载荷系数输入::ITM-MEA-019::输入";
            attribute portName : String = "车辆载荷系数输入";
            attribute direction : String = "输入";
            attribute activeStatus : Boolean = true;
        }
    }
    part def P_N_7225 {
        attribute productCode : String = "7225";
        attribute chineseName : String = "控制电磁阀";
        attribute level : Integer = 4;
        attribute parentCode : String = "7220";
        attribute role : String = "standard_299";
        attribute sourceType : String = "standard_299";
        attribute selected : Boolean = true;
        attribute leaf : Boolean = true;
        port rp_f6a9fd98bacfc4e3 : PT_PT_PHY_008 {
            attribute sourcePortId : String = "PORT::7225::主风压缩空气端口::ITM-PHY-008::双向物理";
            attribute portName : String = "主风压缩空气端口";
            attribute direction : String = "双向物理";
            attribute activeStatus : Boolean = true;
        }
        port rp_99bc109c3b70dfed : PT_PT_PHY_009 {
            attribute sourcePortId : String = "PORT::7225::制动控制压缩空气端口::ITM-PHY-009::双向物理";
            attribute portName : String = "制动控制压缩空气端口";
            attribute direction : String = "双向物理";
            attribute activeStatus : Boolean = true;
        }
        port rp_8e705d6c34197ff6 : ~PT_PT_CMD_022 {
            attribute sourcePortId : String = "PORT::7225::制动电磁阀指令输入::ITM-CMD-022::输入";
            attribute portName : String = "制动电磁阀指令输入";
            attribute direction : String = "输入";
            attribute activeStatus : Boolean = true;
        }
    }
    part def P_N_7226 {
        attribute productCode : String = "7226";
        attribute chineseName : String = "紧急制动阀";
        attribute level : Integer = 4;
        attribute parentCode : String = "7220";
        attribute role : String = "standard_299";
        attribute sourceType : String = "standard_299";
        attribute selected : Boolean = true;
        attribute leaf : Boolean = true;
        port rp_5cccca40a5c3ac4f : PT_PT_PHY_008 {
            attribute sourcePortId : String = "PORT::7226::主风压缩空气端口::ITM-PHY-008::双向物理";
            attribute portName : String = "主风压缩空气端口";
            attribute direction : String = "双向物理";
            attribute activeStatus : Boolean = true;
        }
        port rp_0f31359846cbf234 : PT_PT_PHY_009 {
            attribute sourcePortId : String = "PORT::7226::制动控制压缩空气端口::ITM-PHY-009::双向物理";
            attribute portName : String = "制动控制压缩空气端口";
            attribute direction : String = "双向物理";
            attribute activeStatus : Boolean = true;
        }
        port rp_afce9ce1d2c43605 : PT_PT_PHY_010 {
            attribute sourcePortId : String = "PORT::7226::制动缸压缩空气端口::ITM-PHY-010::双向物理";
            attribute portName : String = "制动缸压缩空气端口";
            attribute direction : String = "双向物理";
            attribute activeStatus : Boolean = true;
        }
        port rp_da93691eb6e6fca4 : ~PT_PT_CMD_030 {
            attribute sourcePortId : String = "PORT::7226::安全停车_制动请求输入::ITM-CMD-030::输入";
            attribute portName : String = "安全停车/制动请求输入";
            attribute direction : String = "输入";
            attribute activeStatus : Boolean = true;
        }
        port rp_5f6a9d81cebde2d3 : ~PT_PT_CMD_004 {
            attribute sourcePortId : String = "PORT::7226::紧急制动请求输入::ITM-CMD-004::输入";
            attribute portName : String = "紧急制动请求输入";
            attribute direction : String = "输入";
            attribute activeStatus : Boolean = true;
        }
    }
    part def P_N_7227 {
        attribute productCode : String = "7227";
        attribute chineseName : String = "缓解阀";
        attribute level : Integer = 4;
        attribute parentCode : String = "7220";
        attribute role : String = "standard_299";
        attribute sourceType : String = "standard_299";
        attribute selected : Boolean = true;
        attribute leaf : Boolean = true;
        port rp_f645a5b55a3683c6 : ~PT_PT_CMD_019 {
            attribute sourcePortId : String = "PORT::7227::制动缓解指令输入::ITM-CMD-019::输入";
            attribute portName : String = "制动缓解指令输入";
            attribute direction : String = "输入";
            attribute activeStatus : Boolean = true;
        }
        port rp_26311db59efd1104 : PT_PT_PHY_010 {
            attribute sourcePortId : String = "PORT::7227::制动缸压缩空气端口::ITM-PHY-010::双向物理";
            attribute portName : String = "制动缸压缩空气端口";
            attribute direction : String = "双向物理";
            attribute activeStatus : Boolean = true;
        }
    }
    part def P_N_7228 {
        attribute productCode : String = "7228";
        attribute chineseName : String = "车厢直接制动截断塞门";
        attribute level : Integer = 4;
        attribute parentCode : String = "7220";
        attribute role : String = "standard_299";
        attribute sourceType : String = "standard_299";
        attribute selected : Boolean = true;
        attribute leaf : Boolean = true;
        port rp_8b8dde76f47ec820 : ~PT_PT_CMD_020 {
            attribute sourcePortId : String = "PORT::7228::制动隔离指令输入::ITM-CMD-020::输入";
            attribute portName : String = "制动隔离指令输入";
            attribute direction : String = "输入";
            attribute activeStatus : Boolean = true;
        }
        port rp_3862b3383cf8bb5b : PT_PT_STA_006 {
            attribute sourcePortId : String = "PORT::7228::制动隔离状态输出::ITM-STA-006::输出";
            attribute portName : String = "制动隔离状态输出";
            attribute direction : String = "输出";
            attribute activeStatus : Boolean = true;
        }
        port rp_e8a2cfb94eeae29a : PT_PT_PHY_010 {
            attribute sourcePortId : String = "PORT::7228::第一气路制动缸压缩空气端口::ITM-PHY-010::双向物理";
            attribute portName : String = "第一气路制动缸压缩空气端口";
            attribute direction : String = "双向物理";
            attribute activeStatus : Boolean = true;
        }
        port rp_9f256ce20a2eedba : PT_PT_PHY_010 {
            attribute sourcePortId : String = "PORT::7228::第二气路制动缸压缩空气端口::ITM-PHY-010::双向物理";
            attribute portName : String = "第二气路制动缸压缩空气端口";
            attribute direction : String = "双向物理";
            attribute activeStatus : Boolean = true;
        }
    }
    part def P_N_7229 {
        attribute productCode : String = "7229";
        attribute chineseName : String = "调压阀";
        attribute level : Integer = 4;
        attribute parentCode : String = "7220";
        attribute role : String = "standard_299";
        attribute sourceType : String = "standard_299";
        attribute selected : Boolean = true;
        attribute leaf : Boolean = true;
        port rp_b38d34e10f750709 : PT_PT_PHY_008 {
            attribute sourcePortId : String = "PORT::7229::主风压缩空气端口::ITM-PHY-008::双向物理";
            attribute portName : String = "主风压缩空气端口";
            attribute direction : String = "双向物理";
            attribute activeStatus : Boolean = true;
        }
        port rp_a8a0abe4af23248d : PT_PT_PHY_009 {
            attribute sourcePortId : String = "PORT::7229::制动控制压缩空气端口::ITM-PHY-009::双向物理";
            attribute portName : String = "制动控制压缩空气端口";
            attribute direction : String = "双向物理";
            attribute activeStatus : Boolean = true;
        }
    }
    part def P_N_722A {
        attribute productCode : String = "722A";
        attribute chineseName : String = "防滑阀组成";
        attribute level : Integer = 4;
        attribute parentCode : String = "7220";
        attribute role : String = "standard_299";
        attribute sourceType : String = "standard_299";
        attribute selected : Boolean = true;
        attribute leaf : Boolean = true;
        port rp_1d96067b68d03c9c : PT_PT_PHY_010 {
            attribute sourcePortId : String = "PORT::722A::上游制动缸压缩空气端口::ITM-PHY-010::双向物理";
            attribute portName : String = "上游制动缸压缩空气端口";
            attribute direction : String = "双向物理";
            attribute activeStatus : Boolean = true;
        }
        port rp_0093bc65af2a8f0a : PT_PT_PHY_010 {
            attribute sourcePortId : String = "PORT::722A::下游制动缸压缩空气端口::ITM-PHY-010::双向物理";
            attribute portName : String = "下游制动缸压缩空气端口";
            attribute direction : String = "双向物理";
            attribute activeStatus : Boolean = true;
        }
        port rp_afe779aaa3b0be62 : ~PT_PT_CMD_023 {
            attribute sourcePortId : String = "PORT::722A::防滑干预指令输入::ITM-CMD-023::输入";
            attribute portName : String = "防滑干预指令输入";
            attribute direction : String = "输入";
            attribute activeStatus : Boolean = true;
        }
        port rp_7d12c51f1034dc2f : PT_PT_STA_011 {
            attribute sourcePortId : String = "PORT::722A::防滑故障状态输出::ITM-STA-011::输出";
            attribute portName : String = "防滑故障状态输出";
            attribute direction : String = "输出";
            attribute activeStatus : Boolean = true;
        }
        port rp_396f6a682ced592d : PT_PT_STA_010 {
            attribute sourcePortId : String = "PORT::722A::防滑激活状态输出::ITM-STA-010::输出";
            attribute portName : String = "防滑激活状态输出";
            attribute direction : String = "输出";
            attribute activeStatus : Boolean = true;
        }
    }
    part def P_N_722B {
        attribute productCode : String = "722B";
        attribute chineseName : String = "压力传感器";
        attribute level : Integer = 4;
        attribute parentCode : String = "7220";
        attribute role : String = "standard_299";
        attribute sourceType : String = "standard_299";
        attribute selected : Boolean = true;
        attribute leaf : Boolean = true;
        port rp_8d219d5375ded80b : PT_PT_MEA_016 {
            attribute sourcePortId : String = "PORT::722B::制动缸压力输出::ITM-MEA-016::输出";
            attribute portName : String = "制动缸压力输出";
            attribute direction : String = "输出";
            attribute activeStatus : Boolean = true;
        }
        port rp_4861b172f136b92e : PT_PT_PHY_010 {
            attribute sourcePortId : String = "PORT::722B::制动缸压缩空气端口::ITM-PHY-010::双向物理";
            attribute portName : String = "制动缸压缩空气端口";
            attribute direction : String = "双向物理";
            attribute activeStatus : Boolean = true;
        }
    }
    part def P_N_722C {
        attribute productCode : String = "722C";
        attribute chineseName : String = "压力开关";
        attribute level : Integer = 4;
        attribute parentCode : String = "7220";
        attribute role : String = "standard_299";
        attribute sourceType : String = "standard_299";
        attribute selected : Boolean = true;
        attribute leaf : Boolean = true;
        port rp_6f3dd380decaae91 : PT_PT_STA_009 {
            attribute sourcePortId : String = "PORT::722C::低风压状态输出::ITM-STA-009::输出";
            attribute portName : String = "低风压状态输出";
            attribute direction : String = "输出";
            attribute activeStatus : Boolean = true;
        }
        port rp_041b8e496fc7f6c1 : PT_PT_PHY_010 {
            attribute sourcePortId : String = "PORT::722C::制动缸压缩空气端口::ITM-PHY-010::双向物理";
            attribute portName : String = "制动缸压缩空气端口";
            attribute direction : String = "双向物理";
            attribute activeStatus : Boolean = true;
        }
    }
    part def P_N_7252 {
        attribute productCode : String = "7252";
        attribute chineseName : String = "非停放制动夹钳装置";
        attribute level : Integer = 4;
        attribute parentCode : String = "7250";
        attribute role : String = "standard_299";
        attribute sourceType : String = "standard_299";
        attribute selected : Boolean = true;
        attribute leaf : Boolean = true;
        port rp_2a185ca8ff0ffb1b : PT_PT_STA_004 {
            attribute sourcePortId : String = "PORT::7252::制动施加状态输出::ITM-STA-004::输出";
            attribute portName : String = "制动施加状态输出";
            attribute direction : String = "输出";
            attribute activeStatus : Boolean = true;
        }
        port rp_8c7b8a7b8f55d796 : PT_PT_STA_005 {
            attribute sourcePortId : String = "PORT::7252::制动缓解状态输出::ITM-STA-005::输出";
            attribute portName : String = "制动缓解状态输出";
            attribute direction : String = "输出";
            attribute activeStatus : Boolean = true;
        }
        port rp_7e02e65996d4ca82 : PT_PT_PHY_010 {
            attribute sourcePortId : String = "PORT::7252::制动缸压缩空气端口::ITM-PHY-010::双向物理";
            attribute portName : String = "制动缸压缩空气端口";
            attribute direction : String = "双向物理";
            attribute activeStatus : Boolean = true;
        }
        port rp_6e046e892954d0de : PT_PT_MEA_017 {
            attribute sourcePortId : String = "PORT::7252::实际摩擦制动力输出::ITM-MEA-017::输出";
            attribute portName : String = "实际摩擦制动力输出";
            attribute direction : String = "输出";
            attribute activeStatus : Boolean = true;
        }
        port rp_b403e112a25e1c53 : PT_PT_PHY_007 {
            attribute sourcePortId : String = "PORT::7252::摩擦制动机械作用端口::ITM-PHY-007::双向物理";
            attribute portName : String = "摩擦制动机械作用端口";
            attribute direction : String = "双向物理";
            attribute activeStatus : Boolean = true;
        }
    }
    part def P_N_7254 {
        attribute productCode : String = "7254";
        attribute chineseName : String = "闸片";
        attribute level : Integer = 4;
        attribute parentCode : String = "7250";
        attribute role : String = "standard_299";
        attribute sourceType : String = "standard_299";
        attribute selected : Boolean = true;
        attribute leaf : Boolean = true;
        port rp_d9511ef0fa1c17df : PT_PT_PHY_007 {
            attribute sourcePortId : String = "PORT::7254::摩擦制动机械作用端口::ITM-PHY-007::双向物理";
            attribute portName : String = "摩擦制动机械作用端口";
            attribute direction : String = "双向物理";
            attribute activeStatus : Boolean = true;
        }
        port rp_7823b5bc99189b72 : PT_PT_ACC_006 {
            attribute sourcePortId : String = "PORT::7254::摩擦制动耗散功率输出::ITM-ACC-006::输出";
            attribute portName : String = "摩擦制动耗散功率输出";
            attribute direction : String = "输出";
            attribute activeStatus : Boolean = true;
        }
        port rp_02c0f1010de52783 : PT_PT_ACC_013 {
            attribute sourcePortId : String = "PORT::7254::摩擦制动耗散累计能量输出::ITM-ACC-013::输出";
            attribute portName : String = "摩擦制动耗散累计能量输出";
            attribute direction : String = "输出";
            attribute activeStatus : Boolean = true;
        }
        port rp_a60f1e83b03ea6d4 : PT_PT_PHY_013 {
            attribute sourcePortId : String = "PORT::7254::热能_热流端口::ITM-PHY-013::双向物理";
            attribute portName : String = "热能/热流端口";
            attribute direction : String = "双向物理";
            attribute activeStatus : Boolean = true;
        }
    }
    part def P_N_7255 {
        attribute productCode : String = "7255";
        attribute chineseName : String = "增压缸";
        attribute level : Integer = 4;
        attribute parentCode : String = "7250";
        attribute role : String = "standard_299";
        attribute sourceType : String = "standard_299";
        attribute selected : Boolean = true;
        attribute leaf : Boolean = true;
        port rp_734246fb536f2b68 : PT_PT_PHY_010 {
            attribute sourcePortId : String = "PORT::7255::制动缸压缩空气端口::ITM-PHY-010::双向物理";
            attribute portName : String = "制动缸压缩空气端口";
            attribute direction : String = "双向物理";
            attribute activeStatus : Boolean = true;
        }
        port rp_4c45e349056154be : PT_PT_PHY_007 {
            attribute sourcePortId : String = "PORT::7255::摩擦制动机械作用端口::ITM-PHY-007::双向物理";
            attribute portName : String = "摩擦制动机械作用端口";
            attribute direction : String = "双向物理";
            attribute activeStatus : Boolean = true;
        }
    }
    part def P_N_7281 {
        attribute productCode : String = "7281";
        attribute chineseName : String = "制动指示器";
        attribute level : Integer = 4;
        attribute parentCode : String = "7280";
        attribute role : String = "standard_299";
        attribute sourceType : String = "standard_299";
        attribute selected : Boolean = true;
        attribute leaf : Boolean = true;
        port rp_2e35e3bc261ab52a : PT_PT_PHY_015 {
            attribute sourcePortId : String = "PORT::7281::低压控制电能端口::ITM-PHY-015::双向物理";
            attribute portName : String = "低压控制电能端口";
            attribute direction : String = "双向物理";
            attribute activeStatus : Boolean = true;
        }
        port rp_b9ead4720ad37cb5 : ~PT_PT_STA_004 {
            attribute sourcePortId : String = "PORT::7281::制动施加状态输入::ITM-STA-004::输入";
            attribute portName : String = "制动施加状态输入";
            attribute direction : String = "输入";
            attribute activeStatus : Boolean = true;
        }
        port rp_28b3abdb6d1d1e9e : ~PT_PT_STA_005 {
            attribute sourcePortId : String = "PORT::7281::制动缓解状态输入::ITM-STA-005::输入";
            attribute portName : String = "制动缓解状态输入";
            attribute direction : String = "输入";
            attribute activeStatus : Boolean = true;
        }
        port rp_5158f71b0a56da87 : ~PT_PT_STA_006 {
            attribute sourcePortId : String = "PORT::7281::制动隔离状态输入::ITM-STA-006::输入";
            attribute portName : String = "制动隔离状态输入";
            attribute direction : String = "输入";
            attribute activeStatus : Boolean = true;
        }
    }
    part def P_N_7284 {
        attribute productCode : String = "7284";
        attribute chineseName : String = "转向架制动截断塞门";
        attribute level : Integer = 4;
        attribute parentCode : String = "7280";
        attribute role : String = "standard_299";
        attribute sourceType : String = "standard_299";
        attribute selected : Boolean = true;
        attribute leaf : Boolean = true;
        port rp_0b1d53051662d3f2 : ~PT_PT_CMD_020 {
            attribute sourcePortId : String = "PORT::7284::制动隔离指令输入::ITM-CMD-020::输入";
            attribute portName : String = "制动隔离指令输入";
            attribute direction : String = "输入";
            attribute activeStatus : Boolean = true;
        }
        port rp_2e5b4d181eadc747 : PT_PT_STA_006 {
            attribute sourcePortId : String = "PORT::7284::制动隔离状态输出::ITM-STA-006::输出";
            attribute portName : String = "制动隔离状态输出";
            attribute direction : String = "输出";
            attribute activeStatus : Boolean = true;
        }
        port rp_c958e15a33eb790f : PT_PT_PHY_010 {
            attribute sourcePortId : String = "PORT::7284::第一气路制动缸压缩空气端口::ITM-PHY-010::双向物理";
            attribute portName : String = "第一气路制动缸压缩空气端口";
            attribute direction : String = "双向物理";
            attribute activeStatus : Boolean = true;
        }
        port rp_3e963340985cb7bd : PT_PT_PHY_010 {
            attribute sourcePortId : String = "PORT::7284::第二气路制动缸压缩空气端口::ITM-PHY-010::双向物理";
            attribute portName : String = "第二气路制动缸压缩空气端口";
            attribute direction : String = "双向物理";
            attribute activeStatus : Boolean = true;
        }
    }
    part def P_N_7285 {
        attribute productCode : String = "7285";
        attribute chineseName : String = "单轴制动截断塞门";
        attribute level : Integer = 4;
        attribute parentCode : String = "7280";
        attribute role : String = "standard_299";
        attribute sourceType : String = "standard_299";
        attribute selected : Boolean = true;
        attribute leaf : Boolean = true;
        port rp_c016d56a46e739fc : ~PT_PT_CMD_020 {
            attribute sourcePortId : String = "PORT::7285::制动隔离指令输入::ITM-CMD-020::输入";
            attribute portName : String = "制动隔离指令输入";
            attribute direction : String = "输入";
            attribute activeStatus : Boolean = true;
        }
        port rp_47c1a16735a84ed9 : PT_PT_STA_006 {
            attribute sourcePortId : String = "PORT::7285::制动隔离状态输出::ITM-STA-006::输出";
            attribute portName : String = "制动隔离状态输出";
            attribute direction : String = "输出";
            attribute activeStatus : Boolean = true;
        }
        port rp_73c5051041203267 : PT_PT_PHY_010 {
            attribute sourcePortId : String = "PORT::7285::第一气路制动缸压缩空气端口::ITM-PHY-010::双向物理";
            attribute portName : String = "第一气路制动缸压缩空气端口";
            attribute direction : String = "双向物理";
            attribute activeStatus : Boolean = true;
        }
        port rp_337ee35177e1c114 : PT_PT_PHY_010 {
            attribute sourcePortId : String = "PORT::7285::第二气路制动缸压缩空气端口::ITM-PHY-010::双向物理";
            attribute portName : String = "第二气路制动缸压缩空气端口";
            attribute direction : String = "双向物理";
            attribute activeStatus : Boolean = true;
        }
    }
    part def P_N_8121 {
        attribute productCode : String = "8121";
        attribute chineseName : String = "主控制单元";
        attribute level : Integer = 4;
        attribute parentCode : String = "8120";
        attribute role : String = "standard_299";
        attribute sourceType : String = "standard_299";
        attribute selected : Boolean = true;
        attribute leaf : Boolean = true;
        port rp_d5423b06aaccb6ac : ~PT_PT_STA_027 {
            attribute sourcePortId : String = "PORT::8121::ATP_外部安全系统状态输入::ITM-STA-027::输入";
            attribute portName : String = "ATP/外部安全系统状态输入";
            attribute direction : String = "输入";
            attribute activeStatus : Boolean = true;
        }
        port rp_d2dfdd1f41baec7a : PT_PT_PHY_015 {
            attribute sourcePortId : String = "PORT::8121::低压控制电能端口::ITM-PHY-015::双向物理";
            attribute portName : String = "低压控制电能端口";
            attribute direction : String = "双向物理";
            attribute activeStatus : Boolean = true;
        }
        port rp_2ee1cd48c6d41ac7 : ~PT_PT_CMD_001 {
            attribute sourcePortId : String = "PORT::8121::列车方向指令输入::ITM-CMD-001::输入";
            attribute portName : String = "列车方向指令输入";
            attribute direction : String = "输入";
            attribute activeStatus : Boolean = true;
        }
        port rp_8fbe2a98ba0ac28c : PT_PT_CMD_001 {
            attribute sourcePortId : String = "PORT::8121::列车方向指令输出::ITM-CMD-001::输出";
            attribute portName : String = "列车方向指令输出";
            attribute direction : String = "输出";
            attribute activeStatus : Boolean = true;
        }
        port rp_ef398de483959e24 : ~PT_PT_MEA_001 {
            attribute sourcePortId : String = "PORT::8121::列车速度输入::ITM-MEA-001::输入";
            attribute portName : String = "列车速度输入";
            attribute direction : String = "输入";
            attribute activeStatus : Boolean = true;
        }
        port rp_36991cec1f7be17b : ~PT_PT_STA_025 {
            attribute sourcePortId : String = "PORT::8121::制动安全回路状态输入::ITM-STA-025::输入";
            attribute portName : String = "制动安全回路状态输入";
            attribute direction : String = "输入";
            attribute activeStatus : Boolean = true;
        }
        port rp_1c14ea3cdc439198 : ~PT_PT_STA_003 {
            attribute sourcePortId : String = "PORT::8121::制动系统可用状态输入::ITM-STA-003::输入";
            attribute portName : String = "制动系统可用状态输入";
            attribute direction : String = "输入";
            attribute activeStatus : Boolean = true;
        }
        port rp_4325db72e2d88769 : ~PT_PT_CMD_030 {
            attribute sourcePortId : String = "PORT::8121::安全停车_制动请求输入::ITM-CMD-030::输入";
            attribute portName : String = "安全停车/制动请求输入";
            attribute direction : String = "输入";
            attribute activeStatus : Boolean = true;
        }
        port rp_0b58c63caeaf2f6d : ~PT_PT_CMD_003 {
            attribute sourcePortId : String = "PORT::8121::服务制动请求输入::ITM-CMD-003::输入";
            attribute portName : String = "服务制动请求输入";
            attribute direction : String = "输入";
            attribute activeStatus : Boolean = true;
        }
        port rp_d82e5c8a7afb4b7b : PT_PT_CMD_003 {
            attribute sourcePortId : String = "PORT::8121::服务制动请求输出::ITM-CMD-003::输出";
            attribute portName : String = "服务制动请求输出";
            attribute direction : String = "输出";
            attribute activeStatus : Boolean = true;
        }
        port rp_f4c8eaaf49d11d3d : PT_PT_CMD_009 {
            attribute sourcePortId : String = "PORT::8121::牵引使能指令输出::ITM-CMD-009::输出";
            attribute portName : String = "牵引使能指令输出";
            attribute direction : String = "输出";
            attribute activeStatus : Boolean = true;
        }
        port rp_c49f12594ff56025 : PT_PT_CMD_008 {
            attribute sourcePortId : String = "PORT::8121::牵引切除请求输出::ITM-CMD-008::输出";
            attribute portName : String = "牵引切除请求输出";
            attribute direction : String = "输出";
            attribute activeStatus : Boolean = true;
        }
        port rp_37e2c2d63c55e098 : ~PT_PT_STA_001 {
            attribute sourcePortId : String = "PORT::8121::牵引可用状态输入::ITM-STA-001::输入";
            attribute portName : String = "牵引可用状态输入";
            attribute direction : String = "输入";
            attribute activeStatus : Boolean = true;
        }
        port rp_de2d35d2bcb08b0b : ~PT_PT_STA_026 {
            attribute sourcePortId : String = "PORT::8121::牵引安全回路状态输入::ITM-STA-026::输入";
            attribute portName : String = "牵引安全回路状态输入";
            attribute direction : String = "输入";
            attribute activeStatus : Boolean = true;
        }
        port rp_a49a67fafe112278 : ~PT_PT_CMD_002 {
            attribute sourcePortId : String = "PORT::8121::牵引指令输入::ITM-CMD-002::输入";
            attribute portName : String = "牵引指令输入";
            attribute direction : String = "输入";
            attribute activeStatus : Boolean = true;
        }
        port rp_809f8275c004ab18 : PT_PT_CMD_002 {
            attribute sourcePortId : String = "PORT::8121::牵引指令输出::ITM-CMD-002::输出";
            attribute portName : String = "牵引指令输出";
            attribute direction : String = "输出";
            attribute activeStatus : Boolean = true;
        }
        port rp_1e34bb2697325127 : ~PT_PT_CMD_004 {
            attribute sourcePortId : String = "PORT::8121::紧急制动请求输入::ITM-CMD-004::输入";
            attribute portName : String = "紧急制动请求输入";
            attribute direction : String = "输入";
            attribute activeStatus : Boolean = true;
        }
        port rp_a9c7eff84933cd80 : PT_PT_CMD_004 {
            attribute sourcePortId : String = "PORT::8121::紧急制动请求输出::ITM-CMD-004::输出";
            attribute portName : String = "紧急制动请求输出";
            attribute direction : String = "输出";
            attribute activeStatus : Boolean = true;
        }
        port rp_2455eff74badb007 : ~PT_PT_STA_024 {
            attribute sourcePortId : String = "PORT::8121::高压安全回路状态输入::ITM-STA-024::输入";
            attribute portName : String = "高压安全回路状态输入";
            attribute direction : String = "输入";
            attribute activeStatus : Boolean = true;
        }
    }
    part def P_N_8122 {
        attribute productCode : String = "8122";
        attribute chineseName : String = "车辆控制单元";
        attribute level : Integer = 4;
        attribute parentCode : String = "8120";
        attribute role : String = "standard_299";
        attribute sourceType : String = "standard_299";
        attribute selected : Boolean = true;
        attribute leaf : Boolean = true;
        port rp_361eac651ec9fd05 : ~PT_PT_MEA_008 {
            attribute sourcePortId : String = "PORT::8122::中间直流母线电压输入::ITM-MEA-008::输入";
            attribute portName : String = "中间直流母线电压输入";
            attribute direction : String = "输入";
            attribute activeStatus : Boolean = true;
        }
        port rp_8b55477454952732 : PT_PT_PHY_015 {
            attribute sourcePortId : String = "PORT::8122::低压控制电能端口::ITM-PHY-015::双向物理";
            attribute portName : String = "低压控制电能端口";
            attribute direction : String = "双向物理";
            attribute activeStatus : Boolean = true;
        }
        port rp_4683a7cb63e55daf : PT_PT_CMD_027 {
            attribute sourcePortId : String = "PORT::8122::储能主接触器指令输出::ITM-CMD-027::输出";
            attribute portName : String = "储能主接触器指令输出";
            attribute direction : String = "输出";
            attribute activeStatus : Boolean = true;
        }
        port rp_77c439392dea95b4 : PT_PT_CMD_025 {
            attribute sourcePortId : String = "PORT::8122::储能功率请求输出::ITM-CMD-025::输出";
            attribute portName : String = "储能功率请求输出";
            attribute direction : String = "输出";
            attribute activeStatus : Boolean = true;
        }
        port rp_8c3ed075d33335e8 : ~PT_PT_LIM_009 {
            attribute sourcePortId : String = "PORT::8122::储能可用充电功率输入::ITM-LIM-009::输入";
            attribute portName : String = "储能可用充电功率输入";
            attribute direction : String = "输入";
            attribute activeStatus : Boolean = true;
        }
        port rp_35b0ef67b409e840 : ~PT_PT_LIM_010 {
            attribute sourcePortId : String = "PORT::8122::储能可用放电功率输入::ITM-LIM-010::输入";
            attribute portName : String = "储能可用放电功率输入";
            attribute direction : String = "输入";
            attribute activeStatus : Boolean = true;
        }
        port rp_a095b9b42ab5cc7d : ~PT_PT_ACC_004 {
            attribute sourcePortId : String = "PORT::8122::储能吸收功率输入::ITM-ACC-004::输入";
            attribute portName : String = "储能吸收功率输入";
            attribute direction : String = "输入";
            attribute activeStatus : Boolean = true;
        }
        port rp_47c78247980cc3a5 : PT_PT_CMD_029 {
            attribute sourcePortId : String = "PORT::8122::储能故障复位指令输出::ITM-CMD-029::输出";
            attribute portName : String = "储能故障复位指令输出";
            attribute direction : String = "输出";
            attribute activeStatus : Boolean = true;
        }
        port rp_1967a947dd39d4a5 : ~PT_PT_STA_030 {
            attribute sourcePortId : String = "PORT::8122::储能系统可用状态输入::ITM-STA-030::输入";
            attribute portName : String = "储能系统可用状态输入";
            attribute direction : String = "输入";
            attribute activeStatus : Boolean = true;
        }
        port rp_9d3500c169fe7103 : ~PT_PT_STA_031 {
            attribute sourcePortId : String = "PORT::8122::储能系统故障状态输入::ITM-STA-031::输入";
            attribute portName : String = "储能系统故障状态输入";
            attribute direction : String = "输入";
            attribute activeStatus : Boolean = true;
        }
        port rp_f704c2e7bab06749 : PT_PT_CMD_028 {
            attribute sourcePortId : String = "PORT::8122::储能预充电指令输出::ITM-CMD-028::输出";
            attribute portName : String = "储能预充电指令输出";
            attribute direction : String = "输出";
            attribute activeStatus : Boolean = true;
        }
        port rp_3aaf955421310ab3 : ~PT_PT_LIM_004 {
            attribute sourcePortId : String = "PORT::8122::再生功率上限输入::ITM-LIM-004::输入";
            attribute portName : String = "再生功率上限输入";
            attribute direction : String = "输入";
            attribute activeStatus : Boolean = true;
        }
        port rp_ac60006ecd824aae : ~PT_PT_CMD_001 {
            attribute sourcePortId : String = "PORT::8122::列车方向指令输入::ITM-CMD-001::输入";
            attribute portName : String = "列车方向指令输入";
            attribute direction : String = "输入";
            attribute activeStatus : Boolean = true;
        }
        port rp_03fc81b8fdcfa7b2 : ~PT_PT_MEA_001 {
            attribute sourcePortId : String = "PORT::8122::列车速度输入::ITM-MEA-001::输入";
            attribute portName : String = "列车速度输入";
            attribute direction : String = "输入";
            attribute activeStatus : Boolean = true;
        }
        port rp_dae173a1561f3f35 : ~PT_PT_ACC_005 {
            attribute sourcePortId : String = "PORT::8122::制动电阻耗散功率输入::ITM-ACC-005::输入";
            attribute portName : String = "制动电阻耗散功率输入";
            attribute direction : String = "输入";
            attribute activeStatus : Boolean = true;
        }
        port rp_b1fb8856841fb7cf : ~PT_PT_STA_003 {
            attribute sourcePortId : String = "PORT::8122::制动系统可用状态输入::ITM-STA-003::输入";
            attribute portName : String = "制动系统可用状态输入";
            attribute direction : String = "输入";
            attribute activeStatus : Boolean = true;
        }
        port rp_ca63e6a6492a217f : ~PT_PT_STA_002 {
            attribute sourcePortId : String = "PORT::8122::动态制动可用状态输入::ITM-STA-002::输入";
            attribute portName : String = "动态制动可用状态输入";
            attribute direction : String = "输入";
            attribute activeStatus : Boolean = true;
        }
        port rp_a4aac084c46e1e57 : PT_PT_CMD_026 {
            attribute sourcePortId : String = "PORT::8122::双向DC_DC使能输出::ITM-CMD-026::输出";
            attribute portName : String = "双向DC/DC使能输出";
            attribute direction : String = "输出";
            attribute activeStatus : Boolean = true;
        }
        port rp_e1808e35289aaba6 : ~PT_PT_MEA_029 {
            attribute sourcePortId : String = "PORT::8122::双向DC_DC实际功率输入::ITM-MEA-029::输入";
            attribute portName : String = "双向DC/DC实际功率输入";
            attribute direction : String = "输入";
            attribute activeStatus : Boolean = true;
        }
        port rp_e0814e233fa0db3e : ~PT_PT_LIM_001 {
            attribute sourcePortId : String = "PORT::8122::可用动态制动力输入::ITM-LIM-001::输入";
            attribute portName : String = "可用动态制动力输入";
            attribute direction : String = "输入";
            attribute activeStatus : Boolean = true;
        }
        port rp_eb1cf5594b5796be : ~PT_PT_ACC_003 {
            attribute sourcePortId : String = "PORT::8122::回馈电网功率输入::ITM-ACC-003::输入";
            attribute portName : String = "回馈电网功率输入";
            attribute direction : String = "输入";
            attribute activeStatus : Boolean = true;
        }
        port rp_ab848f3c1a74117a : ~PT_PT_CMD_030 {
            attribute sourcePortId : String = "PORT::8122::安全停车_制动请求输入::ITM-CMD-030::输入";
            attribute portName : String = "安全停车/制动请求输入";
            attribute direction : String = "输入";
            attribute activeStatus : Boolean = true;
        }
        port rp_bd78e8d84d334672 : ~PT_PT_ACC_002 {
            attribute sourcePortId : String = "PORT::8122::实际再生功率输入::ITM-ACC-002::输入";
            attribute portName : String = "实际再生功率输入";
            attribute direction : String = "输入";
            attribute activeStatus : Boolean = true;
        }
        port rp_f36629c6f163833f : ~PT_PT_MEA_013 {
            attribute sourcePortId : String = "PORT::8122::实际动态制动力输入::ITM-MEA-013::输入";
            attribute portName : String = "实际动态制动力输入";
            attribute direction : String = "输入";
            attribute activeStatus : Boolean = true;
        }
        port rp_abc36140248d0eef : ~PT_PT_LIM_005 {
            attribute sourcePortId : String = "PORT::8122::接触网可接收功率输入::ITM-LIM-005::输入";
            attribute portName : String = "接触网可接收功率输入";
            attribute direction : String = "输入";
            attribute activeStatus : Boolean = true;
        }
        port rp_f0886e48bf75472f : PT_PT_CMD_024 {
            attribute sourcePortId : String = "PORT::8122::撒砂请求输出::ITM-CMD-024::输出";
            attribute portName : String = "撒砂请求输出";
            attribute direction : String = "输出";
            attribute activeStatus : Boolean = true;
        }
        port rp_898e3aba50ea7cb4 : ~PT_PT_CMD_003 {
            attribute sourcePortId : String = "PORT::8122::服务制动请求输入::ITM-CMD-003::输入";
            attribute portName : String = "服务制动请求输入";
            attribute direction : String = "输入";
            attribute activeStatus : Boolean = true;
        }
        port rp_43a34d07ce05b457 : PT_PT_CMD_009 {
            attribute sourcePortId : String = "PORT::8122::牵引使能指令输出::ITM-CMD-009::输出";
            attribute portName : String = "牵引使能指令输出";
            attribute direction : String = "输出";
            attribute activeStatus : Boolean = true;
        }
        port rp_7df2943f24bd3f24 : PT_PT_CMD_008 {
            attribute sourcePortId : String = "PORT::8122::牵引切除请求输出::ITM-CMD-008::输出";
            attribute portName : String = "牵引切除请求输出";
            attribute direction : String = "输出";
            attribute activeStatus : Boolean = true;
        }
        port rp_81e596aab3f0fe4c : ~PT_PT_STA_019 {
            attribute sourcePortId : String = "PORT::8122::牵引变流器故障状态输入::ITM-STA-019::输入";
            attribute portName : String = "牵引变流器故障状态输入";
            attribute direction : String = "输入";
            attribute activeStatus : Boolean = true;
        }
        port rp_b6a69bd683685d04 : ~PT_PT_STA_001 {
            attribute sourcePortId : String = "PORT::8122::牵引可用状态输入::ITM-STA-001::输入";
            attribute portName : String = "牵引可用状态输入";
            attribute direction : String = "输入";
            attribute activeStatus : Boolean = true;
        }
        port rp_c39f0a202834bb12 : ~PT_PT_CMD_002 {
            attribute sourcePortId : String = "PORT::8122::牵引指令输入::ITM-CMD-002::输入";
            attribute portName : String = "牵引指令输入";
            attribute direction : String = "输入";
            attribute activeStatus : Boolean = true;
        }
        port rp_361e7dc74e9287e3 : ~PT_PT_CMD_004 {
            attribute sourcePortId : String = "PORT::8122::紧急制动请求输入::ITM-CMD-004::输入";
            attribute portName : String = "紧急制动请求输入";
            attribute direction : String = "输入";
            attribute activeStatus : Boolean = true;
        }
        port rp_b11b9e2ada11927e : ~PT_PT_ACC_015 {
            attribute sourcePortId : String = "PORT::8122::能量回收率输入::ITM-ACC-015::输入";
            attribute portName : String = "能量回收率输入";
            attribute direction : String = "输入";
            attribute activeStatus : Boolean = true;
        }
        port rp_6437aa0577c9ccd7 : ~PT_PT_MEA_028 {
            attribute sourcePortId : String = "PORT::8122::超级电容SOC输入::ITM-MEA-028::输入";
            attribute portName : String = "超级电容SOC输入";
            attribute direction : String = "输入";
            attribute activeStatus : Boolean = true;
        }
    }
    part def P_N_8125 {
        attribute productCode : String = "8125";
        attribute chineseName : String = "列车级牵引控制单元";
        attribute level : Integer = 4;
        attribute parentCode : String = "8120";
        attribute role : String = "standard_299";
        attribute sourceType : String = "standard_299";
        attribute selected : Boolean = true;
        attribute leaf : Boolean = true;
        port rp_7262595caaf3b8d8 : ~PT_PT_MEA_008 {
            attribute sourcePortId : String = "PORT::8125::中间直流母线电压输入::ITM-MEA-008::输入";
            attribute portName : String = "中间直流母线电压输入";
            attribute direction : String = "输入";
            attribute activeStatus : Boolean = true;
        }
        port rp_5184547f4558dae5 : PT_PT_PHY_015 {
            attribute sourcePortId : String = "PORT::8125::低压控制电能端口::ITM-PHY-015::双向物理";
            attribute portName : String = "低压控制电能端口";
            attribute direction : String = "双向物理";
            attribute activeStatus : Boolean = true;
        }
        port rp_91d8f479934c65da : PT_PT_LIM_004 {
            attribute sourcePortId : String = "PORT::8125::再生功率上限输出::ITM-LIM-004::输出";
            attribute portName : String = "再生功率上限输出";
            attribute direction : String = "输出";
            attribute activeStatus : Boolean = true;
        }
        port rp_4cfbda9683c8c299 : ~PT_PT_MEA_001 {
            attribute sourcePortId : String = "PORT::8125::列车速度输入::ITM-MEA-001::输入";
            attribute portName : String = "列车速度输入";
            attribute direction : String = "输入";
            attribute activeStatus : Boolean = true;
        }
        port rp_d69905c106b65d8f : ~PT_PT_CMD_006 {
            attribute sourcePortId : String = "PORT::8125::动态制动力请求输入::ITM-CMD-006::输入";
            attribute portName : String = "动态制动力请求输入";
            attribute direction : String = "输入";
            attribute activeStatus : Boolean = true;
        }
        port rp_dae11d7502a6c37a : PT_PT_STA_002 {
            attribute sourcePortId : String = "PORT::8125::动态制动可用状态输出::ITM-STA-002::输出";
            attribute portName : String = "动态制动可用状态输出";
            attribute direction : String = "输出";
            attribute activeStatus : Boolean = true;
        }
        port rp_b60dd66dcfd10afa : PT_PT_LIM_001 {
            attribute sourcePortId : String = "PORT::8125::可用动态制动力输出::ITM-LIM-001::输出";
            attribute portName : String = "可用动态制动力输出";
            attribute direction : String = "输出";
            attribute activeStatus : Boolean = true;
        }
        port rp_36a59f5828d4c515 : PT_PT_MEA_013 {
            attribute sourcePortId : String = "PORT::8125::实际动态制动力输出::ITM-MEA-013::输出";
            attribute portName : String = "实际动态制动力输出";
            attribute direction : String = "输出";
            attribute activeStatus : Boolean = true;
        }
        port rp_1809c94f1581c7f8 : ~PT_PT_LIM_005 {
            attribute sourcePortId : String = "PORT::8125::接触网可接收功率输入::ITM-LIM-005::输入";
            attribute portName : String = "接触网可接收功率输入";
            attribute direction : String = "输入";
            attribute activeStatus : Boolean = true;
        }
        port rp_19dfe907fce085c5 : PT_PT_LIM_003 {
            attribute sourcePortId : String = "PORT::8125::牵引_再生转矩上限输出::ITM-LIM-003::输出";
            attribute portName : String = "牵引/再生转矩上限输出";
            attribute direction : String = "输出";
            attribute activeStatus : Boolean = true;
        }
        port rp_0e01f3a589418f6c : ~PT_PT_CMD_009 {
            attribute sourcePortId : String = "PORT::8125::牵引使能指令输入::ITM-CMD-009::输入";
            attribute portName : String = "牵引使能指令输入";
            attribute direction : String = "输入";
            attribute activeStatus : Boolean = true;
        }
        port rp_d86bd7909c634e71 : ~PT_PT_CMD_008 {
            attribute sourcePortId : String = "PORT::8125::牵引切除请求输入::ITM-CMD-008::输入";
            attribute portName : String = "牵引切除请求输入";
            attribute direction : String = "输入";
            attribute activeStatus : Boolean = true;
        }
        port rp_03e482bfcbcb37c1 : PT_PT_STA_019 {
            attribute sourcePortId : String = "PORT::8125::牵引变流器故障状态输出::ITM-STA-019::输出";
            attribute portName : String = "牵引变流器故障状态输出";
            attribute direction : String = "输出";
            attribute activeStatus : Boolean = true;
        }
        port rp_04f0621818e40445 : PT_PT_STA_001 {
            attribute sourcePortId : String = "PORT::8125::牵引可用状态输出::ITM-STA-001::输出";
            attribute portName : String = "牵引可用状态输出";
            attribute direction : String = "输出";
            attribute activeStatus : Boolean = true;
        }
        port rp_90deb6e5a4e470f1 : ~PT_PT_STA_026 {
            attribute sourcePortId : String = "PORT::8125::牵引安全回路状态输入::ITM-STA-026::输入";
            attribute portName : String = "牵引安全回路状态输入";
            attribute direction : String = "输入";
            attribute activeStatus : Boolean = true;
        }
        port rp_713c697d47d94da9 : ~PT_PT_CMD_002 {
            attribute sourcePortId : String = "PORT::8125::牵引指令输入::ITM-CMD-002::输入";
            attribute portName : String = "牵引指令输入";
            attribute direction : String = "输入";
            attribute activeStatus : Boolean = true;
        }
        port rp_1faca3fc4ff0e741 : ~PT_PT_MEA_012 {
            attribute sourcePortId : String = "PORT::8125::牵引电机实际转矩输入::ITM-MEA-012::输入";
            attribute portName : String = "牵引电机实际转矩输入";
            attribute direction : String = "输入";
            attribute activeStatus : Boolean = true;
        }
        port rp_70a8e2c4b0887b4d : PT_PT_CMD_012 {
            attribute sourcePortId : String = "PORT::8125::牵引电机转矩请求输出::ITM-CMD-012::输出";
            attribute portName : String = "牵引电机转矩请求输出";
            attribute direction : String = "输出";
            attribute activeStatus : Boolean = true;
        }
        port rp_4e582bfad9ebbf1d : ~PT_PT_MEA_004 {
            attribute sourcePortId : String = "PORT::8125::牵引电机转速输入::ITM-MEA-004::输入";
            attribute portName : String = "牵引电机转速输入";
            attribute direction : String = "输入";
            attribute activeStatus : Boolean = true;
        }
        port rp_0964720b73edce27 : PT_PT_STA_018 {
            attribute sourcePortId : String = "PORT::8125::电机侧变流器状态输出::ITM-STA-018::输出";
            attribute portName : String = "电机侧变流器状态输出";
            attribute direction : String = "输出";
            attribute activeStatus : Boolean = true;
        }
        port rp_aa028339300f4dbf : PT_PT_STA_017 {
            attribute sourcePortId : String = "PORT::8125::网侧变流器状态输出::ITM-STA-017::输出";
            attribute portName : String = "网侧变流器状态输出";
            attribute direction : String = "输出";
            attribute activeStatus : Boolean = true;
        }
    }
    part def P_N_8127 {
        attribute productCode : String = "8127";
        attribute chineseName : String = "ATP接口单元";
        attribute level : Integer = 4;
        attribute parentCode : String = "8120";
        attribute role : String = "standard_299";
        attribute sourceType : String = "standard_299";
        attribute selected : Boolean = true;
        attribute leaf : Boolean = true;
        port rp_a916a9847aeadebb : ~PT_PT_STA_027 {
            attribute sourcePortId : String = "PORT::8127::ATP_外部安全系统状态输入::ITM-STA-027::输入";
            attribute portName : String = "ATP/外部安全系统状态输入";
            attribute direction : String = "输入";
            attribute activeStatus : Boolean = true;
        }
        port rp_a5398c912a371abd : PT_PT_STA_027 {
            attribute sourcePortId : String = "PORT::8127::ATP_外部安全系统状态输出::ITM-STA-027::输出";
            attribute portName : String = "ATP/外部安全系统状态输出";
            attribute direction : String = "输出";
            attribute activeStatus : Boolean = true;
        }
        port rp_903b55a0b6383446 : PT_PT_PHY_015 {
            attribute sourcePortId : String = "PORT::8127::低压控制电能端口::ITM-PHY-015::双向物理";
            attribute portName : String = "低压控制电能端口";
            attribute direction : String = "双向物理";
            attribute activeStatus : Boolean = true;
        }
        port rp_be0fc7194a7f0161 : ~PT_PT_CMD_030 {
            attribute sourcePortId : String = "PORT::8127::安全停车_制动请求输入::ITM-CMD-030::输入";
            attribute portName : String = "安全停车/制动请求输入";
            attribute direction : String = "输入";
            attribute activeStatus : Boolean = true;
        }
        port rp_8f3091a86214dd4e : PT_PT_CMD_030 {
            attribute sourcePortId : String = "PORT::8127::安全停车_制动请求输出::ITM-CMD-030::输出";
            attribute portName : String = "安全停车/制动请求输出";
            attribute direction : String = "输出";
            attribute activeStatus : Boolean = true;
        }
    }
    part def P_N_8128 {
        attribute productCode : String = "8128";
        attribute chineseName : String = "输入输出单元";
        attribute level : Integer = 4;
        attribute parentCode : String = "8120";
        attribute role : String = "standard_299";
        attribute sourceType : String = "standard_299";
        attribute selected : Boolean = true;
        attribute leaf : Boolean = true;
        port rp_ce6397cb7b81dd94 : ~PT_PT_STA_027 {
            attribute sourcePortId : String = "PORT::8128::ATP_外部安全系统状态输入::ITM-STA-027::输入";
            attribute portName : String = "ATP/外部安全系统状态输入";
            attribute direction : String = "输入";
            attribute activeStatus : Boolean = true;
        }
        port rp_58e3c9dfabb04a51 : PT_PT_STA_027 {
            attribute sourcePortId : String = "PORT::8128::ATP_外部安全系统状态输出::ITM-STA-027::输出";
            attribute portName : String = "ATP/外部安全系统状态输出";
            attribute direction : String = "输出";
            attribute activeStatus : Boolean = true;
        }
        port rp_3b5ccced6e75cf2c : PT_PT_PHY_015 {
            attribute sourcePortId : String = "PORT::8128::低压控制电能端口::ITM-PHY-015::双向物理";
            attribute portName : String = "低压控制电能端口";
            attribute direction : String = "双向物理";
            attribute activeStatus : Boolean = true;
        }
        port rp_eea6ab94a057e9f5 : ~PT_PT_STA_025 {
            attribute sourcePortId : String = "PORT::8128::制动安全回路状态输入::ITM-STA-025::输入";
            attribute portName : String = "制动安全回路状态输入";
            attribute direction : String = "输入";
            attribute activeStatus : Boolean = true;
        }
        port rp_9f2f985b6764bfa7 : PT_PT_STA_025 {
            attribute sourcePortId : String = "PORT::8128::制动安全回路状态输出::ITM-STA-025::输出";
            attribute portName : String = "制动安全回路状态输出";
            attribute direction : String = "输出";
            attribute activeStatus : Boolean = true;
        }
        port rp_cc7a917501039195 : ~PT_PT_MEA_016 {
            attribute sourcePortId : String = "PORT::8128::制动缸压力输入::ITM-MEA-016::输入";
            attribute portName : String = "制动缸压力输入";
            attribute direction : String = "输入";
            attribute activeStatus : Boolean = true;
        }
        port rp_0e19632016b69ff2 : PT_PT_MEA_016 {
            attribute sourcePortId : String = "PORT::8128::制动缸压力输出::ITM-MEA-016::输出";
            attribute portName : String = "制动缸压力输出";
            attribute direction : String = "输出";
            attribute activeStatus : Boolean = true;
        }
        port rp_ccc90acd04ba0ccc : ~PT_PT_MEA_014 {
            attribute sourcePortId : String = "PORT::8128::总风管压力输入::ITM-MEA-014::输入";
            attribute portName : String = "总风管压力输入";
            attribute direction : String = "输入";
            attribute activeStatus : Boolean = true;
        }
        port rp_8d19f6989a5bebad : PT_PT_MEA_014 {
            attribute sourcePortId : String = "PORT::8128::总风管压力输出::ITM-MEA-014::输出";
            attribute portName : String = "总风管压力输出";
            attribute direction : String = "输出";
            attribute activeStatus : Boolean = true;
        }
        port rp_26589bfc82ed6979 : ~PT_PT_CMD_024 {
            attribute sourcePortId : String = "PORT::8128::撒砂请求输入::ITM-CMD-024::输入";
            attribute portName : String = "撒砂请求输入";
            attribute direction : String = "输入";
            attribute activeStatus : Boolean = true;
        }
        port rp_5accd69f9c3a8b0c : PT_PT_CMD_024 {
            attribute sourcePortId : String = "PORT::8128::撒砂请求输出::ITM-CMD-024::输出";
            attribute portName : String = "撒砂请求输出";
            attribute direction : String = "输出";
            attribute activeStatus : Boolean = true;
        }
        port rp_9819959a053f9c06 : ~PT_PT_STA_026 {
            attribute sourcePortId : String = "PORT::8128::牵引安全回路状态输入::ITM-STA-026::输入";
            attribute portName : String = "牵引安全回路状态输入";
            attribute direction : String = "输入";
            attribute activeStatus : Boolean = true;
        }
        port rp_aad98cbe8fa3b27e : PT_PT_STA_026 {
            attribute sourcePortId : String = "PORT::8128::牵引安全回路状态输出::ITM-STA-026::输出";
            attribute portName : String = "牵引安全回路状态输出";
            attribute direction : String = "输出";
            attribute activeStatus : Boolean = true;
        }
        port rp_ff26e108accb1302 : ~PT_PT_MEA_027 {
            attribute sourcePortId : String = "PORT::8128::超级电容温度输入::ITM-MEA-027::输入";
            attribute portName : String = "超级电容温度输入";
            attribute direction : String = "输入";
            attribute activeStatus : Boolean = true;
        }
        port rp_90dd8ed220cd5019 : PT_PT_MEA_027 {
            attribute sourcePortId : String = "PORT::8128::超级电容温度输出::ITM-MEA-027::输出";
            attribute portName : String = "超级电容温度输出";
            attribute direction : String = "输出";
            attribute activeStatus : Boolean = true;
        }
        port rp_51db14413b84b1f3 : ~PT_PT_MEA_025 {
            attribute sourcePortId : String = "PORT::8128::超级电容电压输入::ITM-MEA-025::输入";
            attribute portName : String = "超级电容电压输入";
            attribute direction : String = "输入";
            attribute activeStatus : Boolean = true;
        }
        port rp_69aee385a3c44822 : PT_PT_MEA_025 {
            attribute sourcePortId : String = "PORT::8128::超级电容电压输出::ITM-MEA-025::输出";
            attribute portName : String = "超级电容电压输出";
            attribute direction : String = "输出";
            attribute activeStatus : Boolean = true;
        }
        port rp_c50cfd567a97f3f6 : ~PT_PT_MEA_026 {
            attribute sourcePortId : String = "PORT::8128::超级电容电流输入::ITM-MEA-026::输入";
            attribute portName : String = "超级电容电流输入";
            attribute direction : String = "输入";
            attribute activeStatus : Boolean = true;
        }
        port rp_bde087e602ad92c8 : PT_PT_MEA_026 {
            attribute sourcePortId : String = "PORT::8128::超级电容电流输出::ITM-MEA-026::输出";
            attribute portName : String = "超级电容电流输出";
            attribute direction : String = "输出";
            attribute activeStatus : Boolean = true;
        }
        port rp_2b9604597ff0c9ac : ~PT_PT_STA_024 {
            attribute sourcePortId : String = "PORT::8128::高压安全回路状态输入::ITM-STA-024::输入";
            attribute portName : String = "高压安全回路状态输入";
            attribute direction : String = "输入";
            attribute activeStatus : Boolean = true;
        }
        port rp_cb74be2d7d4a54c7 : PT_PT_STA_024 {
            attribute sourcePortId : String = "PORT::8128::高压安全回路状态输出::ITM-STA-024::输出";
            attribute portName : String = "高压安全回路状态输出";
            attribute direction : String = "输出";
            attribute activeStatus : Boolean = true;
        }
    }
    part def P_N_8151 {
        attribute productCode : String = "8151";
        attribute chineseName : String = "高压安全回路";
        attribute level : Integer = 4;
        attribute parentCode : String = "8150";
        attribute role : String = "standard_299";
        attribute sourceType : String = "standard_299";
        attribute selected : Boolean = true;
        attribute leaf : Boolean = true;
        port rp_b128738a40d9fcd8 : PT_PT_PHY_015 {
            attribute sourcePortId : String = "PORT::8151::低压控制电能端口::ITM-PHY-015::双向物理";
            attribute portName : String = "低压控制电能端口";
            attribute direction : String = "双向物理";
            attribute activeStatus : Boolean = true;
        }
        port rp_c6902e30a0122c0e : PT_PT_STA_024 {
            attribute sourcePortId : String = "PORT::8151::高压安全回路状态输出::ITM-STA-024::输出";
            attribute portName : String = "高压安全回路状态输出";
            attribute direction : String = "输出";
            attribute activeStatus : Boolean = true;
        }
        port rp_d7d7f4cb9554ff03 : ~PT_PT_CMD_016 {
            attribute sourcePortId : String = "PORT::8151::高压断路器指令输入::ITM-CMD-016::输入";
            attribute portName : String = "高压断路器指令输入";
            attribute direction : String = "输入";
            attribute activeStatus : Boolean = true;
        }
    }
    part def P_N_8152 {
        attribute productCode : String = "8152";
        attribute chineseName : String = "制动安全回路";
        attribute level : Integer = 4;
        attribute parentCode : String = "8150";
        attribute role : String = "standard_299";
        attribute sourceType : String = "standard_299";
        attribute selected : Boolean = true;
        attribute leaf : Boolean = true;
        port rp_1e9ebcfb3cef3e9d : PT_PT_PHY_015 {
            attribute sourcePortId : String = "PORT::8152::低压控制电能端口::ITM-PHY-015::双向物理";
            attribute portName : String = "低压控制电能端口";
            attribute direction : String = "双向物理";
            attribute activeStatus : Boolean = true;
        }
        port rp_ae53feffb1e116e3 : PT_PT_STA_025 {
            attribute sourcePortId : String = "PORT::8152::制动安全回路状态输出::ITM-STA-025::输出";
            attribute portName : String = "制动安全回路状态输出";
            attribute direction : String = "输出";
            attribute activeStatus : Boolean = true;
        }
        port rp_1e4f882572b04df5 : ~PT_PT_CMD_030 {
            attribute sourcePortId : String = "PORT::8152::安全停车_制动请求输入::ITM-CMD-030::输入";
            attribute portName : String = "安全停车/制动请求输入";
            attribute direction : String = "输入";
            attribute activeStatus : Boolean = true;
        }
        port rp_93024c6ed1623fbd : ~PT_PT_CMD_004 {
            attribute sourcePortId : String = "PORT::8152::紧急制动请求输入::ITM-CMD-004::输入";
            attribute portName : String = "紧急制动请求输入";
            attribute direction : String = "输入";
            attribute activeStatus : Boolean = true;
        }
    }
    part def P_N_8154 {
        attribute productCode : String = "8154";
        attribute chineseName : String = "牵引安全回路";
        attribute level : Integer = 4;
        attribute parentCode : String = "8150";
        attribute role : String = "standard_299";
        attribute sourceType : String = "standard_299";
        attribute selected : Boolean = true;
        attribute leaf : Boolean = true;
        port rp_caee94e6ee66a74d : PT_PT_PHY_015 {
            attribute sourcePortId : String = "PORT::8154::低压控制电能端口::ITM-PHY-015::双向物理";
            attribute portName : String = "低压控制电能端口";
            attribute direction : String = "双向物理";
            attribute activeStatus : Boolean = true;
        }
        port rp_c3d327abebd9ecfd : ~PT_PT_CMD_009 {
            attribute sourcePortId : String = "PORT::8154::牵引使能指令输入::ITM-CMD-009::输入";
            attribute portName : String = "牵引使能指令输入";
            attribute direction : String = "输入";
            attribute activeStatus : Boolean = true;
        }
        port rp_a8fff2340df81262 : ~PT_PT_CMD_008 {
            attribute sourcePortId : String = "PORT::8154::牵引切除请求输入::ITM-CMD-008::输入";
            attribute portName : String = "牵引切除请求输入";
            attribute direction : String = "输入";
            attribute activeStatus : Boolean = true;
        }
        port rp_492d0ced994652db : PT_PT_STA_026 {
            attribute sourcePortId : String = "PORT::8154::牵引安全回路状态输出::ITM-STA-026::输出";
            attribute portName : String = "牵引安全回路状态输出";
            attribute direction : String = "输出";
            attribute activeStatus : Boolean = true;
        }
    }
    part def P_N_8166 {
        attribute productCode : String = "8166";
        attribute chineseName : String = "能量计";
        attribute level : Integer = 4;
        attribute parentCode : String = "8160";
        attribute role : String = "standard_299";
        attribute sourceType : String = "standard_299";
        attribute selected : Boolean = true;
        attribute leaf : Boolean = true;
        port rp_54d624d57f57843b : ~PT_PT_MEA_008 {
            attribute sourcePortId : String = "PORT::8166::中间直流母线电压输入::ITM-MEA-008::输入";
            attribute portName : String = "中间直流母线电压输入";
            attribute direction : String = "输入";
            attribute activeStatus : Boolean = true;
        }
        port rp_3b0068559b0ca1e4 : ~PT_PT_MEA_009 {
            attribute sourcePortId : String = "PORT::8166::中间直流母线电流输入::ITM-MEA-009::输入";
            attribute portName : String = "中间直流母线电流输入";
            attribute direction : String = "输入";
            attribute activeStatus : Boolean = true;
        }
        port rp_937652db70f809a4 : PT_PT_PHY_015 {
            attribute sourcePortId : String = "PORT::8166::低压控制电能端口::ITM-PHY-015::双向物理";
            attribute portName : String = "低压控制电能端口";
            attribute direction : String = "双向物理";
            attribute activeStatus : Boolean = true;
        }
        port rp_c9c2903288a07ce0 : PT_PT_ACC_004 {
            attribute sourcePortId : String = "PORT::8166::储能吸收功率输出::ITM-ACC-004::输出";
            attribute portName : String = "储能吸收功率输出";
            attribute direction : String = "输出";
            attribute activeStatus : Boolean = true;
        }
        port rp_99ca9a9fac8f0100 : PT_PT_ACC_010 {
            attribute sourcePortId : String = "PORT::8166::储能吸收累计能量输出::ITM-ACC-010::输出";
            attribute portName : String = "储能吸收累计能量输出";
            attribute direction : String = "输出";
            attribute activeStatus : Boolean = true;
        }
        port rp_68e6377e6e18805d : PT_PT_ACC_011 {
            attribute sourcePortId : String = "PORT::8166::储能释放累计能量输出::ITM-ACC-011::输出";
            attribute portName : String = "储能释放累计能量输出";
            attribute direction : String = "输出";
            attribute activeStatus : Boolean = true;
        }
        port rp_936489b6fefaa1dd : PT_PT_ACC_008 {
            attribute sourcePortId : String = "PORT::8166::再生发电累计能量输出::ITM-ACC-008::输出";
            attribute portName : String = "再生发电累计能量输出";
            attribute direction : String = "输出";
            attribute activeStatus : Boolean = true;
        }
        port rp_7f2cae313a3e901f : PT_PT_ACC_005 {
            attribute sourcePortId : String = "PORT::8166::制动电阻耗散功率输出::ITM-ACC-005::输出";
            attribute portName : String = "制动电阻耗散功率输出";
            attribute direction : String = "输出";
            attribute activeStatus : Boolean = true;
        }
        port rp_468a13002030f7d1 : PT_PT_ACC_012 {
            attribute sourcePortId : String = "PORT::8166::制动电阻耗散累计能量输出::ITM-ACC-012::输出";
            attribute portName : String = "制动电阻耗散累计能量输出";
            attribute direction : String = "输出";
            attribute activeStatus : Boolean = true;
        }
        port rp_92ee631b1d7b853f : PT_PT_ACC_014 {
            attribute sourcePortId : String = "PORT::8166::可用制动能量输出::ITM-ACC-014::输出";
            attribute portName : String = "可用制动能量输出";
            attribute direction : String = "输出";
            attribute activeStatus : Boolean = true;
        }
        port rp_945f0734d7cfa81c : PT_PT_ACC_003 {
            attribute sourcePortId : String = "PORT::8166::回馈电网功率输出::ITM-ACC-003::输出";
            attribute portName : String = "回馈电网功率输出";
            attribute direction : String = "输出";
            attribute activeStatus : Boolean = true;
        }
        port rp_80b4c9ee273dda42 : PT_PT_ACC_009 {
            attribute sourcePortId : String = "PORT::8166::回馈电网累计能量输出::ITM-ACC-009::输出";
            attribute portName : String = "回馈电网累计能量输出";
            attribute direction : String = "输出";
            attribute activeStatus : Boolean = true;
        }
        port rp_69cd6c357d586ed9 : PT_PT_ACC_002 {
            attribute sourcePortId : String = "PORT::8166::实际再生功率输出::ITM-ACC-002::输出";
            attribute portName : String = "实际再生功率输出";
            attribute direction : String = "输出";
            attribute activeStatus : Boolean = true;
        }
        port rp_26114df564348068 : PT_PT_ACC_001 {
            attribute sourcePortId : String = "PORT::8166::牵引实际功率输出::ITM-ACC-001::输出";
            attribute portName : String = "牵引实际功率输出";
            attribute direction : String = "输出";
            attribute activeStatus : Boolean = true;
        }
        port rp_f60bfecb427b2161 : PT_PT_ACC_007 {
            attribute sourcePortId : String = "PORT::8166::牵引累计能量输出::ITM-ACC-007::输出";
            attribute portName : String = "牵引累计能量输出";
            attribute direction : String = "输出";
            attribute activeStatus : Boolean = true;
        }
        port rp_0d75944292125dac : PT_PT_ACC_015 {
            attribute sourcePortId : String = "PORT::8166::能量回收率输出::ITM-ACC-015::输出";
            attribute portName : String = "能量回收率输出";
            attribute direction : String = "输出";
            attribute activeStatus : Boolean = true;
        }
        port rp_99f8b39a6442250d : PT_PT_STA_035 {
            attribute sourcePortId : String = "PORT::8166::能量计量有效状态输出::ITM-STA-035::输出";
            attribute portName : String = "能量计量有效状态输出";
            attribute direction : String = "输出";
            attribute activeStatus : Boolean = true;
        }
        port rp_573e029523ef9946 : ~PT_PT_MEA_005 {
            attribute sourcePortId : String = "PORT::8166::高压线路电压输入::ITM-MEA-005::输入";
            attribute portName : String = "高压线路电压输入";
            attribute direction : String = "输入";
            attribute activeStatus : Boolean = true;
        }
        port rp_d9d89be1583c0e18 : ~PT_PT_MEA_006 {
            attribute sourcePortId : String = "PORT::8166::高压线路电流输入::ITM-MEA-006::输入";
            attribute portName : String = "高压线路电流输入";
            attribute direction : String = "输入";
            attribute activeStatus : Boolean = true;
        }
    }
    part def P_D112 {
        attribute productCode : String = "D112";
        attribute chineseName : String = "方向操作元件";
        attribute level : Integer = 4;
        attribute parentCode : String = "D110";
        attribute role : String = "project_extension";
        attribute sourceType : String = "project_extension";
        attribute selected : Boolean = true;
        attribute leaf : Boolean = true;
        port rp_8962dea15ad904c6 : PT_PT_CMD_001 {
            attribute sourcePortId : String = "PORT::D112::列车方向指令输出::ITM-CMD-001::输出";
            attribute portName : String = "列车方向指令输出";
            attribute direction : String = "输出";
            attribute activeStatus : Boolean = true;
        }
    }
    part def P_D113 {
        attribute productCode : String = "D113";
        attribute chineseName : String = "牵引操作元件";
        attribute level : Integer = 4;
        attribute parentCode : String = "D110";
        attribute role : String = "project_extension";
        attribute sourceType : String = "project_extension";
        attribute selected : Boolean = true;
        attribute leaf : Boolean = true;
        port rp_9ca0d9d396f8ffd0 : PT_PT_CMD_002 {
            attribute sourcePortId : String = "PORT::D113::牵引指令输出::ITM-CMD-002::输出";
            attribute portName : String = "牵引指令输出";
            attribute direction : String = "输出";
            attribute activeStatus : Boolean = true;
        }
    }
    part def P_D114 {
        attribute productCode : String = "D114";
        attribute chineseName : String = "制动操作元件";
        attribute level : Integer = 4;
        attribute parentCode : String = "D110";
        attribute role : String = "project_extension";
        attribute sourceType : String = "project_extension";
        attribute selected : Boolean = true;
        attribute leaf : Boolean = true;
        port rp_d3d5739989ecf2dd : PT_PT_CMD_003 {
            attribute sourcePortId : String = "PORT::D114::服务制动请求输出::ITM-CMD-003::输出";
            attribute portName : String = "服务制动请求输出";
            attribute direction : String = "输出";
            attribute activeStatus : Boolean = true;
        }
    }
    part def P_D121 {
        attribute productCode : String = "D121";
        attribute chineseName : String = "紧急制动按钮";
        attribute level : Integer = 4;
        attribute parentCode : String = "D120";
        attribute role : String = "project_extension";
        attribute sourceType : String = "project_extension";
        attribute selected : Boolean = true;
        attribute leaf : Boolean = true;
        port rp_d32b32814a84a88a : PT_PT_CMD_004 {
            attribute sourcePortId : String = "PORT::D121::紧急制动请求输出::ITM-CMD-004::输出";
            attribute portName : String = "紧急制动请求输出";
            attribute direction : String = "输出";
            attribute activeStatus : Boolean = true;
        }
    }
    part def P_D13B {
        attribute productCode : String = "D13B";
        attribute chineseName : String = "撒砂按钮";
        attribute level : Integer = 4;
        attribute parentCode : String = "D130";
        attribute role : String = "project_extension";
        attribute sourceType : String = "project_extension";
        attribute selected : Boolean = true;
        attribute leaf : Boolean = true;
        port rp_9e466471f9387ad5 : PT_PT_CMD_024 {
            attribute sourcePortId : String = "PORT::D13B::撒砂请求输出::ITM-CMD-024::输出";
            attribute portName : String = "撒砂请求输出";
            attribute direction : String = "输出";
            attribute activeStatus : Boolean = true;
        }
    }
    part def P_X111 {
        attribute productCode : String = "X111";
        attribute chineseName : String = "双向DC/DC变流模块";
        attribute level : Integer = 4;
        attribute parentCode : String = "X110";
        attribute role : String = "project_extension";
        attribute sourceType : String = "project_extension";
        attribute selected : Boolean = true;
        attribute leaf : Boolean = true;
        port rp_565c4036e651287e : PT_PT_PHY_003 {
            attribute sourcePortId : String = "PORT::X111::中间直流电能端口::ITM-PHY-003::双向物理";
            attribute portName : String = "中间直流电能端口";
            attribute direction : String = "双向物理";
            attribute activeStatus : Boolean = true;
        }
        port rp_f6cc38ed3ebf357f : PT_PT_PHY_016 {
            attribute sourcePortId : String = "PORT::X111::储能侧直流电能端口::ITM-PHY-016::双向物理";
            attribute portName : String = "储能侧直流电能端口";
            attribute direction : String = "双向物理";
            attribute activeStatus : Boolean = true;
        }
        port rp_3ad794182f43f4d8 : ~PT_PT_CMD_025 {
            attribute sourcePortId : String = "PORT::X111::储能功率请求输入::ITM-CMD-025::输入";
            attribute portName : String = "储能功率请求输入";
            attribute direction : String = "输入";
            attribute activeStatus : Boolean = true;
        }
        port rp_6085b3266f1baf9d : ~PT_PT_CMD_026 {
            attribute sourcePortId : String = "PORT::X111::双向DC_DC使能输入::ITM-CMD-026::输入";
            attribute portName : String = "双向DC/DC使能输入";
            attribute direction : String = "输入";
            attribute activeStatus : Boolean = true;
        }
        port rp_9828766df3df1904 : PT_PT_MEA_029 {
            attribute sourcePortId : String = "PORT::X111::双向DC_DC实际功率输出::ITM-MEA-029::输出";
            attribute portName : String = "双向DC/DC实际功率输出";
            attribute direction : String = "输出";
            attribute activeStatus : Boolean = true;
        }
        port rp_121334297c7e5c44 : PT_PT_STA_029 {
            attribute sourcePortId : String = "PORT::X111::双向DC_DC故障状态输出::ITM-STA-029::输出";
            attribute portName : String = "双向DC/DC故障状态输出";
            attribute direction : String = "输出";
            attribute activeStatus : Boolean = true;
        }
        port rp_fbc8c24ae8a5bcdd : PT_PT_STA_028 {
            attribute sourcePortId : String = "PORT::X111::双向DC_DC状态输出::ITM-STA-028::输出";
            attribute portName : String = "双向DC/DC状态输出";
            attribute direction : String = "输出";
            attribute activeStatus : Boolean = true;
        }
        port rp_74c67e7bc95576e6 : PT_PT_MEA_030 {
            attribute sourcePortId : String = "PORT::X111::双向DC_DC电流输出::ITM-MEA-030::输出";
            attribute portName : String = "双向DC/DC电流输出";
            attribute direction : String = "输出";
            attribute activeStatus : Boolean = true;
        }
    }
    part def P_X112 {
        attribute productCode : String = "X112";
        attribute chineseName : String = "双向DC/DC控制模块";
        attribute level : Integer = 4;
        attribute parentCode : String = "X110";
        attribute role : String = "project_extension";
        attribute sourceType : String = "project_extension";
        attribute selected : Boolean = true;
        attribute leaf : Boolean = true;
        port rp_89849c49127b2dfb : ~PT_PT_MEA_008 {
            attribute sourcePortId : String = "PORT::X112::中间直流母线电压输入::ITM-MEA-008::输入";
            attribute portName : String = "中间直流母线电压输入";
            attribute direction : String = "输入";
            attribute activeStatus : Boolean = true;
        }
        port rp_569130817376da24 : PT_PT_PHY_015 {
            attribute sourcePortId : String = "PORT::X112::低压控制电能端口::ITM-PHY-015::双向物理";
            attribute portName : String = "低压控制电能端口";
            attribute direction : String = "双向物理";
            attribute activeStatus : Boolean = true;
        }
        port rp_81f1c1da5d6d3173 : ~PT_PT_CMD_027 {
            attribute sourcePortId : String = "PORT::X112::储能主接触器指令输入::ITM-CMD-027::输入";
            attribute portName : String = "储能主接触器指令输入";
            attribute direction : String = "输入";
            attribute activeStatus : Boolean = true;
        }
        port rp_2ea4241545e6ca09 : PT_PT_CMD_027 {
            attribute sourcePortId : String = "PORT::X112::储能主接触器指令输出::ITM-CMD-027::输出";
            attribute portName : String = "储能主接触器指令输出";
            attribute direction : String = "输出";
            attribute activeStatus : Boolean = true;
        }
        port rp_f929a9fa6b633837 : ~PT_PT_STA_032 {
            attribute sourcePortId : String = "PORT::X112::储能主接触器状态输入::ITM-STA-032::输入";
            attribute portName : String = "储能主接触器状态输入";
            attribute direction : String = "输入";
            attribute activeStatus : Boolean = true;
        }
        port rp_00da2edc928b715d : ~PT_PT_STA_034 {
            attribute sourcePortId : String = "PORT::X112::储能保护跳闸状态输入::ITM-STA-034::输入";
            attribute portName : String = "储能保护跳闸状态输入";
            attribute direction : String = "输入";
            attribute activeStatus : Boolean = true;
        }
        port rp_843fa8c83311440e : ~PT_PT_CMD_025 {
            attribute sourcePortId : String = "PORT::X112::储能功率请求输入::ITM-CMD-025::输入";
            attribute portName : String = "储能功率请求输入";
            attribute direction : String = "输入";
            attribute activeStatus : Boolean = true;
        }
        port rp_1ca011606f062f80 : PT_PT_CMD_025 {
            attribute sourcePortId : String = "PORT::X112::储能功率请求输出::ITM-CMD-025::输出";
            attribute portName : String = "储能功率请求输出";
            attribute direction : String = "输出";
            attribute activeStatus : Boolean = true;
        }
        port rp_388d943a537916a7 : PT_PT_LIM_009 {
            attribute sourcePortId : String = "PORT::X112::储能可用充电功率输出::ITM-LIM-009::输出";
            attribute portName : String = "储能可用充电功率输出";
            attribute direction : String = "输出";
            attribute activeStatus : Boolean = true;
        }
        port rp_73067cce4e6a7eeb : PT_PT_LIM_010 {
            attribute sourcePortId : String = "PORT::X112::储能可用放电功率输出::ITM-LIM-010::输出";
            attribute portName : String = "储能可用放电功率输出";
            attribute direction : String = "输出";
            attribute activeStatus : Boolean = true;
        }
        port rp_a59821acb0d73604 : PT_PT_ACC_004 {
            attribute sourcePortId : String = "PORT::X112::储能吸收功率输出::ITM-ACC-004::输出";
            attribute portName : String = "储能吸收功率输出";
            attribute direction : String = "输出";
            attribute activeStatus : Boolean = true;
        }
        port rp_b84f02a624b9982f : ~PT_PT_CMD_029 {
            attribute sourcePortId : String = "PORT::X112::储能故障复位指令输入::ITM-CMD-029::输入";
            attribute portName : String = "储能故障复位指令输入";
            attribute direction : String = "输入";
            attribute activeStatus : Boolean = true;
        }
        port rp_3b946767139d884a : PT_PT_STA_030 {
            attribute sourcePortId : String = "PORT::X112::储能系统可用状态输出::ITM-STA-030::输出";
            attribute portName : String = "储能系统可用状态输出";
            attribute direction : String = "输出";
            attribute activeStatus : Boolean = true;
        }
        port rp_e5eadfefaf46ac0a : PT_PT_STA_031 {
            attribute sourcePortId : String = "PORT::X112::储能系统故障状态输出::ITM-STA-031::输出";
            attribute portName : String = "储能系统故障状态输出";
            attribute direction : String = "输出";
            attribute activeStatus : Boolean = true;
        }
        port rp_5ff890136d5d49bf : ~PT_PT_CMD_028 {
            attribute sourcePortId : String = "PORT::X112::储能预充电指令输入::ITM-CMD-028::输入";
            attribute portName : String = "储能预充电指令输入";
            attribute direction : String = "输入";
            attribute activeStatus : Boolean = true;
        }
        port rp_adb78cdbb75469df : PT_PT_CMD_028 {
            attribute sourcePortId : String = "PORT::X112::储能预充电指令输出::ITM-CMD-028::输出";
            attribute portName : String = "储能预充电指令输出";
            attribute direction : String = "输出";
            attribute activeStatus : Boolean = true;
        }
        port rp_3ecd9966c9972a7e : ~PT_PT_STA_033 {
            attribute sourcePortId : String = "PORT::X112::储能预充电状态输入::ITM-STA-033::输入";
            attribute portName : String = "储能预充电状态输入";
            attribute direction : String = "输入";
            attribute activeStatus : Boolean = true;
        }
        port rp_1164249ec859b807 : ~PT_PT_CMD_026 {
            attribute sourcePortId : String = "PORT::X112::双向DC_DC使能输入::ITM-CMD-026::输入";
            attribute portName : String = "双向DC/DC使能输入";
            attribute direction : String = "输入";
            attribute activeStatus : Boolean = true;
        }
        port rp_f980a38f780089b6 : PT_PT_CMD_026 {
            attribute sourcePortId : String = "PORT::X112::双向DC_DC使能输出::ITM-CMD-026::输出";
            attribute portName : String = "双向DC/DC使能输出";
            attribute direction : String = "输出";
            attribute activeStatus : Boolean = true;
        }
        port rp_4659cbe7e3b50b58 : ~PT_PT_MEA_029 {
            attribute sourcePortId : String = "PORT::X112::双向DC_DC实际功率输入::ITM-MEA-029::输入";
            attribute portName : String = "双向DC/DC实际功率输入";
            attribute direction : String = "输入";
            attribute activeStatus : Boolean = true;
        }
        port rp_d8c491383c9a24dc : PT_PT_STA_029 {
            attribute sourcePortId : String = "PORT::X112::双向DC_DC故障状态输出::ITM-STA-029::输出";
            attribute portName : String = "双向DC/DC故障状态输出";
            attribute direction : String = "输出";
            attribute activeStatus : Boolean = true;
        }
        port rp_96349f1cf75b3d94 : PT_PT_STA_028 {
            attribute sourcePortId : String = "PORT::X112::双向DC_DC状态输出::ITM-STA-028::输出";
            attribute portName : String = "双向DC/DC状态输出";
            attribute direction : String = "输出";
            attribute activeStatus : Boolean = true;
        }
        port rp_88bb7293920adfa8 : ~PT_PT_MEA_030 {
            attribute sourcePortId : String = "PORT::X112::双向DC_DC电流输入::ITM-MEA-030::输入";
            attribute portName : String = "双向DC/DC电流输入";
            attribute direction : String = "输入";
            attribute activeStatus : Boolean = true;
        }
        port rp_1f01277587ee6905 : ~PT_PT_LIM_007 {
            attribute sourcePortId : String = "PORT::X112::直流母线电压上限输入::ITM-LIM-007::输入";
            attribute portName : String = "直流母线电压上限输入";
            attribute direction : String = "输入";
            attribute activeStatus : Boolean = true;
        }
        port rp_ced58e17348ff578 : ~PT_PT_MEA_028 {
            attribute sourcePortId : String = "PORT::X112::超级电容SOC输入::ITM-MEA-028::输入";
            attribute portName : String = "超级电容SOC输入";
            attribute direction : String = "输入";
            attribute activeStatus : Boolean = true;
        }
        port rp_0dcfac1fe8bbd763 : PT_PT_LIM_011 {
            attribute sourcePortId : String = "PORT::X112::超级电容充电允许状态输出::ITM-LIM-011::输出";
            attribute portName : String = "超级电容充电允许状态输出";
            attribute direction : String = "输出";
            attribute activeStatus : Boolean = true;
        }
        port rp_651a62a644935ccb : PT_PT_LIM_012 {
            attribute sourcePortId : String = "PORT::X112::超级电容放电允许状态输出::ITM-LIM-012::输出";
            attribute portName : String = "超级电容放电允许状态输出";
            attribute direction : String = "输出";
            attribute activeStatus : Boolean = true;
        }
        port rp_848f140649f8e2ae : ~PT_PT_MEA_027 {
            attribute sourcePortId : String = "PORT::X112::超级电容温度输入::ITM-MEA-027::输入";
            attribute portName : String = "超级电容温度输入";
            attribute direction : String = "输入";
            attribute activeStatus : Boolean = true;
        }
        port rp_fc5798a77b6a020d : ~PT_PT_MEA_025 {
            attribute sourcePortId : String = "PORT::X112::超级电容电压输入::ITM-MEA-025::输入";
            attribute portName : String = "超级电容电压输入";
            attribute direction : String = "输入";
            attribute activeStatus : Boolean = true;
        }
        port rp_e8341f592e73af5e : ~PT_PT_MEA_026 {
            attribute sourcePortId : String = "PORT::X112::超级电容电流输入::ITM-MEA-026::输入";
            attribute portName : String = "超级电容电流输入";
            attribute direction : String = "输入";
            attribute activeStatus : Boolean = true;
        }
    }
    part def P_X113 {
        attribute productCode : String = "X113";
        attribute chineseName : String = "双向DC/DC检测保护组件";
        attribute level : Integer = 4;
        attribute parentCode : String = "X110";
        attribute role : String = "project_extension";
        attribute sourceType : String = "project_extension";
        attribute selected : Boolean = true;
        attribute leaf : Boolean = true;
        port rp_0e45c7ab357a42e6 : PT_PT_MEA_008 {
            attribute sourcePortId : String = "PORT::X113::中间直流母线电压输出::ITM-MEA-008::输出";
            attribute portName : String = "中间直流母线电压输出";
            attribute direction : String = "输出";
            attribute activeStatus : Boolean = true;
        }
        port rp_571e6f079e1116ac : PT_PT_PHY_003 {
            attribute sourcePortId : String = "PORT::X113::中间直流电能端口::ITM-PHY-003::双向物理";
            attribute portName : String = "中间直流电能端口";
            attribute direction : String = "双向物理";
            attribute activeStatus : Boolean = true;
        }
        port rp_9f0c62635f9ae105 : PT_PT_PHY_015 {
            attribute sourcePortId : String = "PORT::X113::低压控制电能端口::ITM-PHY-015::双向物理";
            attribute portName : String = "低压控制电能端口";
            attribute direction : String = "双向物理";
            attribute activeStatus : Boolean = true;
        }
        port rp_5e8b7419342ecb12 : PT_PT_PHY_016 {
            attribute sourcePortId : String = "PORT::X113::储能侧直流电能端口::ITM-PHY-016::双向物理";
            attribute portName : String = "储能侧直流电能端口";
            attribute direction : String = "双向物理";
            attribute activeStatus : Boolean = true;
        }
        port rp_fdb7d950b1296be2 : PT_PT_STA_034 {
            attribute sourcePortId : String = "PORT::X113::储能保护跳闸状态输出::ITM-STA-034::输出";
            attribute portName : String = "储能保护跳闸状态输出";
            attribute direction : String = "输出";
            attribute activeStatus : Boolean = true;
        }
        port rp_bbb42fe7ea40668f : PT_PT_LIM_009 {
            attribute sourcePortId : String = "PORT::X113::储能可用充电功率输出::ITM-LIM-009::输出";
            attribute portName : String = "储能可用充电功率输出";
            attribute direction : String = "输出";
            attribute activeStatus : Boolean = true;
        }
        port rp_1a2f8620b785c434 : PT_PT_LIM_010 {
            attribute sourcePortId : String = "PORT::X113::储能可用放电功率输出::ITM-LIM-010::输出";
            attribute portName : String = "储能可用放电功率输出";
            attribute direction : String = "输出";
            attribute activeStatus : Boolean = true;
        }
        port rp_b96276443bd011b6 : PT_PT_STA_031 {
            attribute sourcePortId : String = "PORT::X113::储能系统故障状态输出::ITM-STA-031::输出";
            attribute portName : String = "储能系统故障状态输出";
            attribute direction : String = "输出";
            attribute activeStatus : Boolean = true;
        }
        port rp_97ac296a7909b915 : PT_PT_STA_029 {
            attribute sourcePortId : String = "PORT::X113::双向DC_DC故障状态输出::ITM-STA-029::输出";
            attribute portName : String = "双向DC/DC故障状态输出";
            attribute direction : String = "输出";
            attribute activeStatus : Boolean = true;
        }
        port rp_30a4f2a71d158c56 : PT_PT_MEA_030 {
            attribute sourcePortId : String = "PORT::X113::双向DC_DC电流输出::ITM-MEA-030::输出";
            attribute portName : String = "双向DC/DC电流输出";
            attribute direction : String = "输出";
            attribute activeStatus : Boolean = true;
        }
        port rp_d9c32040ebe6917e : PT_PT_LIM_007 {
            attribute sourcePortId : String = "PORT::X113::直流母线电压上限输出::ITM-LIM-007::输出";
            attribute portName : String = "直流母线电压上限输出";
            attribute direction : String = "输出";
            attribute activeStatus : Boolean = true;
        }
        port rp_180c13c086da3d55 : PT_PT_MEA_027 {
            attribute sourcePortId : String = "PORT::X113::超级电容温度输出::ITM-MEA-027::输出";
            attribute portName : String = "超级电容温度输出";
            attribute direction : String = "输出";
            attribute activeStatus : Boolean = true;
        }
        port rp_5926a6f58d47dc95 : PT_PT_MEA_025 {
            attribute sourcePortId : String = "PORT::X113::超级电容电压输出::ITM-MEA-025::输出";
            attribute portName : String = "超级电容电压输出";
            attribute direction : String = "输出";
            attribute activeStatus : Boolean = true;
        }
        port rp_2f7c47b1b3242c83 : PT_PT_MEA_026 {
            attribute sourcePortId : String = "PORT::X113::超级电容电流输出::ITM-MEA-026::输出";
            attribute portName : String = "超级电容电流输出";
            attribute direction : String = "输出";
            attribute activeStatus : Boolean = true;
        }
    }
    part def P_X121 {
        attribute productCode : String = "X121";
        attribute chineseName : String = "超级电容模块";
        attribute level : Integer = 4;
        attribute parentCode : String = "X120";
        attribute role : String = "project_extension";
        attribute sourceType : String = "project_extension";
        attribute selected : Boolean = true;
        attribute leaf : Boolean = true;
        port rp_e7b0b50420861015 : PT_PT_PHY_016 {
            attribute sourcePortId : String = "PORT::X121::储能侧直流电能端口::ITM-PHY-016::双向物理";
            attribute portName : String = "储能侧直流电能端口";
            attribute direction : String = "双向物理";
            attribute activeStatus : Boolean = true;
        }
        port rp_387cdae1b4483182 : PT_PT_PHY_013 {
            attribute sourcePortId : String = "PORT::X121::热能_热流端口::ITM-PHY-013::双向物理";
            attribute portName : String = "热能/热流端口";
            attribute direction : String = "双向物理";
            attribute activeStatus : Boolean = true;
        }
        port rp_b6cf5a49ced52abf : PT_PT_MEA_028 {
            attribute sourcePortId : String = "PORT::X121::超级电容SOC输出::ITM-MEA-028::输出";
            attribute portName : String = "超级电容SOC输出";
            attribute direction : String = "输出";
            attribute activeStatus : Boolean = true;
        }
    }
    part def P_X122 {
        attribute productCode : String = "X122";
        attribute chineseName : String = "超级电容电压传感器";
        attribute level : Integer = 4;
        attribute parentCode : String = "X120";
        attribute role : String = "project_extension";
        attribute sourceType : String = "project_extension";
        attribute selected : Boolean = true;
        attribute leaf : Boolean = true;
        port rp_0b3c69b37f8b252c : PT_PT_PHY_016 {
            attribute sourcePortId : String = "PORT::X122::储能侧直流电能端口::ITM-PHY-016::双向物理";
            attribute portName : String = "储能侧直流电能端口";
            attribute direction : String = "双向物理";
            attribute activeStatus : Boolean = true;
        }
        port rp_370359531bcbeddd : PT_PT_MEA_025 {
            attribute sourcePortId : String = "PORT::X122::超级电容电压输出::ITM-MEA-025::输出";
            attribute portName : String = "超级电容电压输出";
            attribute direction : String = "输出";
            attribute activeStatus : Boolean = true;
        }
    }
    part def P_X123 {
        attribute productCode : String = "X123";
        attribute chineseName : String = "超级电容电流传感器";
        attribute level : Integer = 4;
        attribute parentCode : String = "X120";
        attribute role : String = "project_extension";
        attribute sourceType : String = "project_extension";
        attribute selected : Boolean = true;
        attribute leaf : Boolean = true;
        port rp_b6c8109cae13eea5 : PT_PT_PHY_016 {
            attribute sourcePortId : String = "PORT::X123::储能侧直流电能端口::ITM-PHY-016::双向物理";
            attribute portName : String = "储能侧直流电能端口";
            attribute direction : String = "双向物理";
            attribute activeStatus : Boolean = true;
        }
        port rp_9b6812b4ca482c66 : PT_PT_MEA_026 {
            attribute sourcePortId : String = "PORT::X123::超级电容电流输出::ITM-MEA-026::输出";
            attribute portName : String = "超级电容电流输出";
            attribute direction : String = "输出";
            attribute activeStatus : Boolean = true;
        }
    }
    part def P_X124 {
        attribute productCode : String = "X124";
        attribute chineseName : String = "超级电容温度传感器";
        attribute level : Integer = 4;
        attribute parentCode : String = "X120";
        attribute role : String = "project_extension";
        attribute sourceType : String = "project_extension";
        attribute selected : Boolean = true;
        attribute leaf : Boolean = true;
        port rp_5083db510ca305a5 : PT_PT_MEA_027 {
            attribute sourcePortId : String = "PORT::X124::超级电容温度输出::ITM-MEA-027::输出";
            attribute portName : String = "超级电容温度输出";
            attribute direction : String = "输出";
            attribute activeStatus : Boolean = true;
        }
        port rp_4d5eafc70549d9c0 : PT_PT_PHY_013 {
            attribute sourcePortId : String = "PORT::X124::超级电容热能感知端口::ITM-PHY-013::双向物理";
            attribute portName : String = "超级电容热能感知端口";
            attribute direction : String = "双向物理";
            attribute activeStatus : Boolean = true;
        }
    }
    part def P_X131 {
        attribute productCode : String = "X131";
        attribute chineseName : String = "储能主接触器";
        attribute level : Integer = 4;
        attribute parentCode : String = "X130";
        attribute role : String = "project_extension";
        attribute sourceType : String = "project_extension";
        attribute selected : Boolean = true;
        attribute leaf : Boolean = true;
        port rp_b06975e1baff62be : ~PT_PT_CMD_027 {
            attribute sourcePortId : String = "PORT::X131::储能主接触器指令输入::ITM-CMD-027::输入";
            attribute portName : String = "储能主接触器指令输入";
            attribute direction : String = "输入";
            attribute activeStatus : Boolean = true;
        }
        port rp_c029b3b1472e957d : PT_PT_STA_032 {
            attribute sourcePortId : String = "PORT::X131::储能主接触器状态输出::ITM-STA-032::输出";
            attribute portName : String = "储能主接触器状态输出";
            attribute direction : String = "输出";
            attribute activeStatus : Boolean = true;
        }
        port rp_ef3e7082da0c5648 : PT_PT_PHY_016 {
            attribute sourcePortId : String = "PORT::X131::母线段储能侧直流电能端口::ITM-PHY-016::双向物理";
            attribute portName : String = "母线段储能侧直流电能端口";
            attribute direction : String = "双向物理";
            attribute activeStatus : Boolean = true;
        }
        port rp_6bdc28fa4761142d : PT_PT_PHY_016 {
            attribute sourcePortId : String = "PORT::X131::负载段储能侧直流电能端口::ITM-PHY-016::双向物理";
            attribute portName : String = "负载段储能侧直流电能端口";
            attribute direction : String = "双向物理";
            attribute activeStatus : Boolean = true;
        }
    }
    part def P_X132 {
        attribute productCode : String = "X132";
        attribute chineseName : String = "储能预充电组件";
        attribute level : Integer = 4;
        attribute parentCode : String = "X130";
        attribute role : String = "project_extension";
        attribute sourceType : String = "project_extension";
        attribute selected : Boolean = true;
        attribute leaf : Boolean = true;
        port rp_4d68d3f9ee4e0009 : ~PT_PT_CMD_028 {
            attribute sourcePortId : String = "PORT::X132::储能预充电指令输入::ITM-CMD-028::输入";
            attribute portName : String = "储能预充电指令输入";
            attribute direction : String = "输入";
            attribute activeStatus : Boolean = true;
        }
        port rp_53191daa39f85d49 : PT_PT_STA_033 {
            attribute sourcePortId : String = "PORT::X132::储能预充电状态输出::ITM-STA-033::输出";
            attribute portName : String = "储能预充电状态输出";
            attribute direction : String = "输出";
            attribute activeStatus : Boolean = true;
        }
        port rp_0fa709507856ec0b : PT_PT_PHY_016 {
            attribute sourcePortId : String = "PORT::X132::预充输入段储能侧直流电能端口::ITM-PHY-016::双向物理";
            attribute portName : String = "预充输入段储能侧直流电能端口";
            attribute direction : String = "双向物理";
            attribute activeStatus : Boolean = true;
        }
        port rp_1d9e411fc4e0ebf9 : PT_PT_PHY_016 {
            attribute sourcePortId : String = "PORT::X132::预充输出段储能侧直流电能端口::ITM-PHY-016::双向物理";
            attribute portName : String = "预充输出段储能侧直流电能端口";
            attribute direction : String = "双向物理";
            attribute activeStatus : Boolean = true;
        }
    }
    part def P_X133 {
        attribute productCode : String = "X133";
        attribute chineseName : String = "储能支路保护组件";
        attribute level : Integer = 4;
        attribute parentCode : String = "X130";
        attribute role : String = "project_extension";
        attribute sourceType : String = "project_extension";
        attribute selected : Boolean = true;
        attribute leaf : Boolean = true;
        port rp_da93423081013940 : PT_PT_PHY_015 {
            attribute sourcePortId : String = "PORT::X133::低压控制电能端口::ITM-PHY-015::双向物理";
            attribute portName : String = "低压控制电能端口";
            attribute direction : String = "双向物理";
            attribute activeStatus : Boolean = true;
        }
        port rp_06282bbd1af76861 : PT_PT_PHY_016 {
            attribute sourcePortId : String = "PORT::X133::保护输入段储能侧直流电能端口::ITM-PHY-016::双向物理";
            attribute portName : String = "保护输入段储能侧直流电能端口";
            attribute direction : String = "双向物理";
            attribute activeStatus : Boolean = true;
        }
        port rp_49a2b1a2497ebf63 : PT_PT_PHY_016 {
            attribute sourcePortId : String = "PORT::X133::保护输出段储能侧直流电能端口::ITM-PHY-016::双向物理";
            attribute portName : String = "保护输出段储能侧直流电能端口";
            attribute direction : String = "双向物理";
            attribute activeStatus : Boolean = true;
        }
        port rp_ffcdb33099ab8a28 : PT_PT_STA_034 {
            attribute sourcePortId : String = "PORT::X133::储能保护跳闸状态输出::ITM-STA-034::输出";
            attribute portName : String = "储能保护跳闸状态输出";
            attribute direction : String = "输出";
            attribute activeStatus : Boolean = true;
        }
        port rp_0ac161b92c0e41a0 : PT_PT_STA_031 {
            attribute sourcePortId : String = "PORT::X133::储能系统故障状态输出::ITM-STA-031::输出";
            attribute portName : String = "储能系统故障状态输出";
            attribute direction : String = "输出";
            attribute activeStatus : Boolean = true;
        }
    }
    part def P_N_3110 {
        attribute productCode : String = "3110";
        attribute chineseName : String = "车轮车轴";
        attribute level : Integer = 3;
        attribute parentCode : String = "3100";
        attribute role : String = "standard_299";
        attribute sourceType : String = "standard_299";
        attribute selected : Boolean = true;
        attribute leaf : Boolean = false;
        part p_N_3111 : P_N_3111;
        part p_N_3112 : P_N_3112;
    }
    part def P_N_3120 {
        attribute productCode : String = "3120";
        attribute chineseName : String = "齿轮箱及附件";
        attribute level : Integer = 3;
        attribute parentCode : String = "3100";
        attribute role : String = "standard_299";
        attribute sourceType : String = "standard_299";
        attribute selected : Boolean = true;
        attribute leaf : Boolean = false;
        part p_N_3121 : P_N_3121;
    }
    part def P_N_3130 {
        attribute productCode : String = "3130";
        attribute chineseName : String = "制动盘";
        attribute level : Integer = 3;
        attribute parentCode : String = "3100";
        attribute role : String = "standard_299";
        attribute sourceType : String = "standard_299";
        attribute selected : Boolean = true;
        attribute leaf : Boolean = false;
        part p_N_3131 : P_N_3131;
        part p_N_3132 : P_N_3132;
        part p_N_3133 : P_N_3133;
    }
    part def P_N_3510 {
        attribute productCode : String = "3510";
        attribute chineseName : String = "传动耦合机构";
        attribute level : Integer = 3;
        attribute parentCode : String = "3500";
        attribute role : String = "standard_299";
        attribute sourceType : String = "standard_299";
        attribute selected : Boolean = true;
        attribute leaf : Boolean = false;
        part p_N_3511 : P_N_3511;
        part p_N_3512 : P_N_3512;
        part p_N_3514 : P_N_3514;
    }
    part def P_N_3640 {
        attribute productCode : String = "3640";
        attribute chineseName : String = "速度检测组件";
        attribute level : Integer = 3;
        attribute parentCode : String = "3600";
        attribute role : String = "standard_299";
        attribute sourceType : String = "standard_299";
        attribute selected : Boolean = true;
        attribute leaf : Boolean = false;
        part p_N_3641 : P_N_3641;
        part p_N_3643 : P_N_3643;
        part p_N_3644 : P_N_3644;
    }
    part def P_N_3810 {
        attribute productCode : String = "3810";
        attribute chineseName : String = "撒砂装置";
        attribute level : Integer = 3;
        attribute parentCode : String = "3800";
        attribute role : String = "standard_299";
        attribute sourceType : String = "standard_299";
        attribute selected : Boolean = true;
        attribute leaf : Boolean = false;
        part p_N_3811 : P_N_3811;
        part p_N_3813 : P_N_3813;
        part p_N_3814 : P_N_3814;
    }
    part def P_N_4110 {
        attribute productCode : String = "4110";
        attribute chineseName : String = "受电弓总成";
        attribute level : Integer = 3;
        attribute parentCode : String = "4100";
        attribute role : String = "standard_299";
        attribute sourceType : String = "standard_299";
        attribute selected : Boolean = true;
        attribute leaf : Boolean = false;
        part p_N_4111 : P_N_4111;
        part p_N_411C : P_N_411C;
    }
    part def P_N_4120 {
        attribute productCode : String = "4120";
        attribute chineseName : String = "其它类型受流组成";
        attribute level : Integer = 3;
        attribute parentCode : String = "4100";
        attribute role : String = "standard_299";
        attribute sourceType : String = "standard_299";
        attribute selected : Boolean = true;
        attribute leaf : Boolean = false;
        part p_N_4121 : P_N_4121;
    }
    part def P_N_4210 {
        attribute productCode : String = "4210";
        attribute chineseName : String = "高压开关";
        attribute level : Integer = 3;
        attribute parentCode : String = "4200";
        attribute role : String = "standard_299";
        attribute sourceType : String = "standard_299";
        attribute selected : Boolean = true;
        attribute leaf : Boolean = false;
        part p_N_4211 : P_N_4211;
        part p_N_4212 : P_N_4212;
    }
    part def P_N_4230 {
        attribute productCode : String = "4230";
        attribute chineseName : String = "高压保护及检测部件";
        attribute level : Integer = 3;
        attribute parentCode : String = "4200";
        attribute role : String = "standard_299";
        attribute sourceType : String = "standard_299";
        attribute selected : Boolean = true;
        attribute leaf : Boolean = false;
        part p_N_4235 : P_N_4235;
        part p_N_4236 : P_N_4236;
        part p_N_4238 : P_N_4238;
        part p_N_4239 : P_N_4239;
    }
    part def P_N_4240 {
        attribute productCode : String = "4240";
        attribute chineseName : String = "能量测量";
        attribute level : Integer = 3;
        attribute parentCode : String = "4200";
        attribute role : String = "standard_299";
        attribute sourceType : String = "standard_299";
        attribute selected : Boolean = true;
        attribute leaf : Boolean = false;
        part p_N_4241 : P_N_4241;
    }
    part def P_N_4410 {
        attribute productCode : String = "4410";
        attribute chineseName : String = "主回路回流设备";
        attribute level : Integer = 3;
        attribute parentCode : String = "4400";
        attribute role : String = "standard_299";
        attribute sourceType : String = "standard_299";
        attribute selected : Boolean = true;
        attribute leaf : Boolean = false;
        part p_N_4411 : P_N_4411;
        part p_N_4412 : P_N_4412;
        part p_N_4413 : P_N_4413;
    }
    part def P_N_4510 {
        attribute productCode : String = "4510";
        attribute chineseName : String = "主变压器主体及其控制";
        attribute level : Integer = 3;
        attribute parentCode : String = "4500";
        attribute role : String = "standard_299";
        attribute sourceType : String = "standard_299";
        attribute selected : Boolean = true;
        attribute leaf : Boolean = false;
        part p_N_4511 : P_N_4511;
        part p_N_4513 : P_N_4513;
        part p_N_4517 : P_N_4517;
        part p_N_4518 : P_N_4518;
    }
    part def P_N_5110 {
        attribute productCode : String = "5110";
        attribute chineseName : String = "牵引变流器控制";
        attribute level : Integer = 3;
        attribute parentCode : String = "5100";
        attribute role : String = "standard_299";
        attribute sourceType : String = "standard_299";
        attribute selected : Boolean = true;
        attribute leaf : Boolean = false;
        part p_N_5111 : P_N_5111;
        part p_N_5112 : P_N_5112;
        part p_N_5113 : P_N_5113;
    }
    part def P_N_5120 {
        attribute productCode : String = "5120";
        attribute chineseName : String = "输入及预充电单元";
        attribute level : Integer = 3;
        attribute parentCode : String = "5100";
        attribute role : String = "standard_299";
        attribute sourceType : String = "standard_299";
        attribute selected : Boolean = true;
        attribute leaf : Boolean = false;
        part p_N_5121 : P_N_5121;
        part p_N_5122 : P_N_5122;
    }
    part def P_N_5130 {
        attribute productCode : String = "5130";
        attribute chineseName : String = "变流模块";
        attribute level : Integer = 3;
        attribute parentCode : String = "5100";
        attribute role : String = "standard_299";
        attribute sourceType : String = "standard_299";
        attribute selected : Boolean = true;
        attribute leaf : Boolean = false;
        part p_N_5131 : P_N_5131;
        part p_N_5132 : P_N_5132;
        part p_N_5133 : P_N_5133;
    }
    part def P_N_5140 {
        attribute productCode : String = "5140";
        attribute chineseName : String = "中间直流环节组件及其";
        attribute level : Integer = 3;
        attribute parentCode : String = "5100";
        attribute role : String = "standard_299";
        attribute sourceType : String = "standard_299";
        attribute selected : Boolean = true;
        attribute leaf : Boolean = false;
        part p_N_5142 : P_N_5142;
        part p_N_5145 : P_N_5145;
    }
    part def P_N_5310 {
        attribute productCode : String = "5310";
        attribute chineseName : String = "牵引电机组成";
        attribute level : Integer = 3;
        attribute parentCode : String = "5300";
        attribute role : String = "standard_299";
        attribute sourceType : String = "standard_299";
        attribute selected : Boolean = true;
        attribute leaf : Boolean = false;
        part p_N_5311 : P_N_5311;
    }
    part def P_N_7120 {
        attribute productCode : String = "7120";
        attribute chineseName : String = "风缸";
        attribute level : Integer = 3;
        attribute parentCode : String = "7100";
        attribute role : String = "standard_299";
        attribute sourceType : String = "standard_299";
        attribute selected : Boolean = true;
        attribute leaf : Boolean = false;
        part p_N_7124 : P_N_7124;
    }
    part def P_N_7130 {
        attribute productCode : String = "7130";
        attribute chineseName : String = "列车级压缩空气分配组件";
        attribute level : Integer = 3;
        attribute parentCode : String = "7100";
        attribute role : String = "standard_299";
        attribute sourceType : String = "standard_299";
        attribute selected : Boolean = true;
        attribute leaf : Boolean = false;
        part p_N_7131 : P_N_7131;
    }
    part def P_N_7140 {
        attribute productCode : String = "7140";
        attribute chineseName : String = "供风压力开关及传感器";
        attribute level : Integer = 3;
        attribute parentCode : String = "7100";
        attribute role : String = "standard_299";
        attribute sourceType : String = "standard_299";
        attribute selected : Boolean = true;
        attribute leaf : Boolean = false;
        part p_N_7142 : P_N_7142;
    }
    part def P_N_7210 {
        attribute productCode : String = "7210";
        attribute chineseName : String = "制动控制组件";
        attribute level : Integer = 3;
        attribute parentCode : String = "7200";
        attribute role : String = "standard_299";
        attribute sourceType : String = "standard_299";
        attribute selected : Boolean = true;
        attribute leaf : Boolean = false;
        part p_N_7211 : P_N_7211;
        part p_N_7213 : P_N_7213;
    }
    part def P_N_7220 {
        attribute productCode : String = "7220";
        attribute chineseName : String = "直接制动控制";
        attribute level : Integer = 3;
        attribute parentCode : String = "7200";
        attribute role : String = "standard_299";
        attribute sourceType : String = "standard_299";
        attribute selected : Boolean = true;
        attribute leaf : Boolean = false;
        part p_N_7222 : P_N_7222;
        part p_N_7223 : P_N_7223;
        part p_N_7224 : P_N_7224;
        part p_N_7225 : P_N_7225;
        part p_N_7226 : P_N_7226;
        part p_N_7227 : P_N_7227;
        part p_N_7228 : P_N_7228;
        part p_N_7229 : P_N_7229;
        part p_N_722A : P_N_722A;
        part p_N_722B : P_N_722B;
        part p_N_722C : P_N_722C;
    }
    part def P_N_7250 {
        attribute productCode : String = "7250";
        attribute chineseName : String = "制动夹钳及其配套组件";
        attribute level : Integer = 3;
        attribute parentCode : String = "7200";
        attribute role : String = "standard_299";
        attribute sourceType : String = "standard_299";
        attribute selected : Boolean = true;
        attribute leaf : Boolean = false;
        part p_N_7252 : P_N_7252;
        part p_N_7254 : P_N_7254;
        part p_N_7255 : P_N_7255;
    }
    part def P_N_7280 {
        attribute productCode : String = "7280";
        attribute chineseName : String = "其它制动元件及附件";
        attribute level : Integer = 3;
        attribute parentCode : String = "7200";
        attribute role : String = "standard_299";
        attribute sourceType : String = "standard_299";
        attribute selected : Boolean = true;
        attribute leaf : Boolean = false;
        part p_N_7281 : P_N_7281;
        part p_N_7284 : P_N_7284;
        part p_N_7285 : P_N_7285;
    }
    part def P_N_8120 {
        attribute productCode : String = "8120";
        attribute chineseName : String = "控制单元及输入输出模块";
        attribute level : Integer = 3;
        attribute parentCode : String = "8100";
        attribute role : String = "standard_299";
        attribute sourceType : String = "standard_299";
        attribute selected : Boolean = true;
        attribute leaf : Boolean = false;
        part p_N_8121 : P_N_8121;
        part p_N_8122 : P_N_8122;
        part p_N_8125 : P_N_8125;
        part p_N_8127 : P_N_8127;
        part p_N_8128 : P_N_8128;
    }
    part def P_N_8150 {
        attribute productCode : String = "8150";
        attribute chineseName : String = "整车级安全回路及其附件";
        attribute level : Integer = 3;
        attribute parentCode : String = "8100";
        attribute role : String = "standard_299";
        attribute sourceType : String = "standard_299";
        attribute selected : Boolean = true;
        attribute leaf : Boolean = false;
        part p_N_8151 : P_N_8151;
        part p_N_8152 : P_N_8152;
        part p_N_8154 : P_N_8154;
    }
    part def P_N_8160 {
        attribute productCode : String = "8160";
        attribute chineseName : String = "其它附件";
        attribute level : Integer = 3;
        attribute parentCode : String = "8100";
        attribute role : String = "standard_299";
        attribute sourceType : String = "standard_299";
        attribute selected : Boolean = true;
        attribute leaf : Boolean = false;
        part p_N_8166 : P_N_8166;
    }
    part def P_D110 {
        attribute productCode : String = "D110";
        attribute chineseName : String = "基本操纵组件";
        attribute level : Integer = 3;
        attribute parentCode : String = "D100";
        attribute role : String = "project_extension";
        attribute sourceType : String = "project_extension";
        attribute selected : Boolean = true;
        attribute leaf : Boolean = false;
        part p_D112 : P_D112;
        part p_D113 : P_D113;
        part p_D114 : P_D114;
    }
    part def P_D120 {
        attribute productCode : String = "D120";
        attribute chineseName : String = "紧急响应元件";
        attribute level : Integer = 3;
        attribute parentCode : String = "D100";
        attribute role : String = "project_extension";
        attribute sourceType : String = "project_extension";
        attribute selected : Boolean = true;
        attribute leaf : Boolean = false;
        part p_D121 : P_D121;
    }
    part def P_D130 {
        attribute productCode : String = "D130";
        attribute chineseName : String = "开关按钮功能组件";
        attribute level : Integer = 3;
        attribute parentCode : String = "D100";
        attribute role : String = "project_extension";
        attribute sourceType : String = "project_extension";
        attribute selected : Boolean = true;
        attribute leaf : Boolean = false;
        part p_D13B : P_D13B;
    }
    part def P_X110 {
        attribute productCode : String = "X110";
        attribute chineseName : String = "双向储能变流及控制";
        attribute level : Integer = 3;
        attribute parentCode : String = "X100";
        attribute role : String = "project_extension";
        attribute sourceType : String = "project_extension";
        attribute selected : Boolean = true;
        attribute leaf : Boolean = false;
        part p_X111 : P_X111;
        part p_X112 : P_X112;
        part p_X113 : P_X113;
    }
    part def P_X120 {
        attribute productCode : String = "X120";
        attribute chineseName : String = "超级电容储能组件";
        attribute level : Integer = 3;
        attribute parentCode : String = "X100";
        attribute role : String = "project_extension";
        attribute sourceType : String = "project_extension";
        attribute selected : Boolean = true;
        attribute leaf : Boolean = false;
        part p_X121 : P_X121;
        part p_X122 : P_X122;
        part p_X123 : P_X123;
        part p_X124 : P_X124;
    }
    part def P_X130 {
        attribute productCode : String = "X130";
        attribute chineseName : String = "储能接入与保护";
        attribute level : Integer = 3;
        attribute parentCode : String = "X100";
        attribute role : String = "project_extension";
        attribute sourceType : String = "project_extension";
        attribute selected : Boolean = true;
        attribute leaf : Boolean = false;
        part p_X131 : P_X131;
        part p_X132 : P_X132;
        part p_X133 : P_X133;
    }
    part def P_N_3100 {
        attribute productCode : String = "3100";
        attribute chineseName : String = "轮轴组成";
        attribute level : Integer = 2;
        attribute parentCode : String = "3000";
        attribute role : String = "standard_299";
        attribute sourceType : String = "standard_299";
        attribute selected : Boolean = true;
        attribute leaf : Boolean = false;
        part p_N_3110 : P_N_3110;
        part p_N_3120 : P_N_3120;
        part p_N_3130 : P_N_3130;
    }
    part def P_N_3500 {
        attribute productCode : String = "3500";
        attribute chineseName : String = "牵引传动耦合组件及其附件";
        attribute level : Integer = 2;
        attribute parentCode : String = "3000";
        attribute role : String = "standard_299";
        attribute sourceType : String = "standard_299";
        attribute selected : Boolean = true;
        attribute leaf : Boolean = false;
        part p_N_3510 : P_N_3510;
    }
    part def P_N_3600 {
        attribute productCode : String = "3600";
        attribute chineseName : String = "转向架相关检测";
        attribute level : Integer = 2;
        attribute parentCode : String = "3000";
        attribute role : String = "standard_299";
        attribute sourceType : String = "standard_299";
        attribute selected : Boolean = true;
        attribute leaf : Boolean = false;
        part p_N_3640 : P_N_3640;
    }
    part def P_N_3800 {
        attribute productCode : String = "3800";
        attribute chineseName : String = "辅助增粘及轮缘润滑";
        attribute level : Integer = 2;
        attribute parentCode : String = "3000";
        attribute role : String = "standard_299";
        attribute sourceType : String = "standard_299";
        attribute selected : Boolean = true;
        attribute leaf : Boolean = false;
        part p_N_3810 : P_N_3810;
    }
    part def P_N_4100 {
        attribute productCode : String = "4100";
        attribute chineseName : String = "高压受流";
        attribute level : Integer = 2;
        attribute parentCode : String = "4000";
        attribute role : String = "standard_299";
        attribute sourceType : String = "standard_299";
        attribute selected : Boolean = true;
        attribute leaf : Boolean = false;
        part p_N_4110 : P_N_4110;
        part p_N_4120 : P_N_4120;
    }
    part def P_N_4200 {
        attribute productCode : String = "4200";
        attribute chineseName : String = "网侧高压分配及控制";
        attribute level : Integer = 2;
        attribute parentCode : String = "4000";
        attribute role : String = "standard_299";
        attribute sourceType : String = "standard_299";
        attribute selected : Boolean = true;
        attribute leaf : Boolean = false;
        part p_N_4210 : P_N_4210;
        part p_N_4230 : P_N_4230;
        part p_N_4240 : P_N_4240;
    }
    part def P_N_4400 {
        attribute productCode : String = "4400";
        attribute chineseName : String = "回流及接地";
        attribute level : Integer = 2;
        attribute parentCode : String = "4000";
        attribute role : String = "standard_299";
        attribute sourceType : String = "standard_299";
        attribute selected : Boolean = true;
        attribute leaf : Boolean = false;
        part p_N_4410 : P_N_4410;
    }
    part def P_N_4500 {
        attribute productCode : String = "4500";
        attribute chineseName : String = "主变压器及其冷却";
        attribute level : Integer = 2;
        attribute parentCode : String = "4000";
        attribute role : String = "standard_299";
        attribute sourceType : String = "standard_299";
        attribute selected : Boolean = true;
        attribute leaf : Boolean = false;
        part p_N_4510 : P_N_4510;
    }
    part def P_N_5100 {
        attribute productCode : String = "5100";
        attribute chineseName : String = "牵引变流器主体及其控制";
        attribute level : Integer = 2;
        attribute parentCode : String = "5000";
        attribute role : String = "standard_299";
        attribute sourceType : String = "standard_299";
        attribute selected : Boolean = true;
        attribute leaf : Boolean = false;
        part p_N_5110 : P_N_5110;
        part p_N_5120 : P_N_5120;
        part p_N_5130 : P_N_5130;
        part p_N_5140 : P_N_5140;
    }
    part def P_N_5300 {
        attribute productCode : String = "5300";
        attribute chineseName : String = "牵引电机及其冷却";
        attribute level : Integer = 2;
        attribute parentCode : String = "5000";
        attribute role : String = "standard_299";
        attribute sourceType : String = "standard_299";
        attribute selected : Boolean = true;
        attribute leaf : Boolean = false;
        part p_N_5310 : P_N_5310;
    }
    part def P_N_7100 {
        attribute productCode : String = "7100";
        attribute chineseName : String = "供风";
        attribute level : Integer = 2;
        attribute parentCode : String = "7000";
        attribute role : String = "standard_299";
        attribute sourceType : String = "standard_299";
        attribute selected : Boolean = true;
        attribute leaf : Boolean = false;
        part p_N_7120 : P_N_7120;
        part p_N_7130 : P_N_7130;
        part p_N_7140 : P_N_7140;
    }
    part def P_N_7200 {
        attribute productCode : String = "7200";
        attribute chineseName : String = "制动";
        attribute level : Integer = 2;
        attribute parentCode : String = "7000";
        attribute role : String = "standard_299";
        attribute sourceType : String = "standard_299";
        attribute selected : Boolean = true;
        attribute leaf : Boolean = false;
        part p_N_7210 : P_N_7210;
        part p_N_7220 : P_N_7220;
        part p_N_7250 : P_N_7250;
        part p_N_7280 : P_N_7280;
    }
    part def P_N_8100 {
        attribute productCode : String = "8100";
        attribute chineseName : String = "列车主干网及安全回路";
        attribute level : Integer = 2;
        attribute parentCode : String = "8000";
        attribute role : String = "standard_299";
        attribute sourceType : String = "standard_299";
        attribute selected : Boolean = true;
        attribute leaf : Boolean = false;
        part p_N_8120 : P_N_8120;
        part p_N_8150 : P_N_8150;
        part p_N_8160 : P_N_8160;
    }
    part def P_D100 {
        attribute productCode : String = "D100";
        attribute chineseName : String = "操纵设施";
        attribute level : Integer = 2;
        attribute parentCode : String = "D000";
        attribute role : String = "project_extension";
        attribute sourceType : String = "project_extension";
        attribute selected : Boolean = true;
        attribute leaf : Boolean = false;
        part p_D110 : P_D110;
        part p_D120 : P_D120;
        part p_D130 : P_D130;
    }
    part def P_E100 {
        attribute productCode : String = "E100";
        attribute chineseName : String = "ATP车载";
        attribute level : Integer = 2;
        attribute parentCode : String = "E000";
        attribute role : String = "external_system";
        attribute sourceType : String = "external_system";
        attribute selected : Boolean = true;
        attribute leaf : Boolean = true;
        port rp_0307dc18d9537f9d : PT_PT_STA_027 {
            attribute sourcePortId : String = "PORT::E100::ATP_外部安全系统状态输出::ITM-STA-027::输出";
            attribute portName : String = "ATP/外部安全系统状态输出";
            attribute direction : String = "输出";
            attribute activeStatus : Boolean = true;
        }
        port rp_7273a171b473f816 : PT_PT_CMD_030 {
            attribute sourcePortId : String = "PORT::E100::安全停车_制动请求输出::ITM-CMD-030::输出";
            attribute portName : String = "安全停车/制动请求输出";
            attribute direction : String = "输出";
            attribute activeStatus : Boolean = true;
        }
    }
    part def P_X100 {
        attribute productCode : String = "X100";
        attribute chineseName : String = "车载再生储能";
        attribute level : Integer = 2;
        attribute parentCode : String = "X000";
        attribute role : String = "project_extension";
        attribute sourceType : String = "project_extension";
        attribute selected : Boolean = true;
        attribute leaf : Boolean = false;
        part p_X110 : P_X110;
        part p_X120 : P_X120;
        part p_X130 : P_X130;
    }
    part def P_N_3000 {
        attribute productCode : String = "3000";
        attribute chineseName : String = "转向架及其辅助";
        attribute level : Integer = 1;
        attribute parentCode : String = "";
        attribute role : String = "standard_299";
        attribute sourceType : String = "standard_299";
        attribute selected : Boolean = true;
        attribute leaf : Boolean = false;
        part p_N_3100 : P_N_3100;
        part p_N_3500 : P_N_3500;
        part p_N_3600 : P_N_3600;
        part p_N_3800 : P_N_3800;
    }
    part def P_N_4000 {
        attribute productCode : String = "4000";
        attribute chineseName : String = "主供电";
        attribute level : Integer = 1;
        attribute parentCode : String = "";
        attribute role : String = "standard_299";
        attribute sourceType : String = "standard_299";
        attribute selected : Boolean = true;
        attribute leaf : Boolean = false;
        part p_N_4100 : P_N_4100;
        part p_N_4200 : P_N_4200;
        part p_N_4400 : P_N_4400;
        part p_N_4500 : P_N_4500;
    }
    part def P_N_5000 {
        attribute productCode : String = "5000";
        attribute chineseName : String = "牵引";
        attribute level : Integer = 1;
        attribute parentCode : String = "";
        attribute role : String = "standard_299";
        attribute sourceType : String = "standard_299";
        attribute selected : Boolean = true;
        attribute leaf : Boolean = false;
        part p_N_5100 : P_N_5100;
        part p_N_5300 : P_N_5300;
    }
    part def P_N_7000 {
        attribute productCode : String = "7000";
        attribute chineseName : String = "供风制动";
        attribute level : Integer = 1;
        attribute parentCode : String = "";
        attribute role : String = "standard_299";
        attribute sourceType : String = "standard_299";
        attribute selected : Boolean = true;
        attribute leaf : Boolean = false;
        part p_N_7100 : P_N_7100;
        part p_N_7200 : P_N_7200;
    }
    part def P_N_8000 {
        attribute productCode : String = "8000";
        attribute chineseName : String = "网络及辅助监控";
        attribute level : Integer = 1;
        attribute parentCode : String = "";
        attribute role : String = "standard_299";
        attribute sourceType : String = "standard_299";
        attribute selected : Boolean = true;
        attribute leaf : Boolean = false;
        part p_N_8100 : P_N_8100;
    }
    part def P_D000 {
        attribute productCode : String = "D000";
        attribute chineseName : String = "驾驶设施";
        attribute level : Integer = 1;
        attribute parentCode : String = "";
        attribute role : String = "project_extension";
        attribute sourceType : String = "project_extension";
        attribute selected : Boolean = true;
        attribute leaf : Boolean = false;
        part p_D100 : P_D100;
    }
    part def P_E000 {
        attribute productCode : String = "E000";
        attribute chineseName : String = "电务车载";
        attribute level : Integer = 1;
        attribute parentCode : String = "";
        attribute role : String = "external_system";
        attribute sourceType : String = "external_system";
        attribute selected : Boolean = true;
        attribute leaf : Boolean = false;
        part p_E100 : P_E100;
    }
    part def P_X000 {
        attribute productCode : String = "X000";
        attribute chineseName : String = "再生储能扩展";
        attribute level : Integer = 1;
        attribute parentCode : String = "";
        attribute role : String = "project_extension";
        attribute sourceType : String = "project_extension";
        attribute selected : Boolean = true;
        attribute leaf : Boolean = false;
        part p_X100 : P_X100;
    }
    part def B_BOUNDARY_CATENARY_25KV :> ExternalBoundaryBase {
        attribute boundaryId : String = "BOUNDARY-CATENARY-25KV";
        attribute boundaryName : String = "External 25 kV AC catenary";
        attribute domain : String = "electrical";
        port bp_6fe914f662252c4d : PT_PT_PHY_001;
    }
    part def B_BOUNDARY_RAIL :> ExternalBoundaryBase {
        attribute boundaryId : String = "BOUNDARY-RAIL";
        attribute boundaryName : String = "Rail mechanical and traction-return boundary";
        attribute domain : String = "mechanical/electrical";
        port bp_cf72f055f5b12b85 : PT_PT_PHY_006;
        port bp_3a29560c03050dbe : PT_PT_PHY_011;
    }
    part def B_BOUNDARY_THERMAL_ENVIRONMENT :> ExternalBoundaryBase {
        attribute boundaryId : String = "BOUNDARY-THERMAL-ENVIRONMENT";
        attribute boundaryName : String = "Ambient thermal sink";
        attribute domain : String = "thermal";
        port bp_2ac3a221090b246a : PT_PT_PHY_013;
    }
    part def RailSystemContext {
        part p_N_3000 : P_N_3000;
        part p_N_4000 : P_N_4000;
        part p_N_5000 : P_N_5000;
        part p_N_7000 : P_N_7000;
        part p_N_8000 : P_N_8000;
        part p_D000 : P_D000;
        part p_E000 : P_E000;
        part p_X000 : P_X000;
        part boundary_BOUNDARY_CATENARY_25KV : B_BOUNDARY_CATENARY_25KV;
        part boundary_BOUNDARY_RAIL : B_BOUNDARY_RAIL;
        part boundary_BOUNDARY_THERMAL_ENVIRONMENT : B_BOUNDARY_THERMAL_ENVIRONMENT;
    }
}

package FunctionDefinitions {
    private import ScalarValues::*;
    private import ItemDefinitions::*;
    action def FN_F_3000_01 {
        attribute functionId : String = "F-3000-01";
        attribute chineseName : String = "转换能量/物理量、控制运行";
        attribute englishName : String = "Convert energy/quantities; Control operation";
        attribute functionLevel : Integer = 1;
        attribute category : String = "COORDINATION";
        attribute allocatedProductCode : String = "3000";
    }
    action def FN_F_3100_01 {
        attribute functionId : String = "F-3100-01";
        attribute chineseName : String = "转换能量/物理量、传递能量/介质";
        attribute englishName : String = "Convert energy/quantities; Transport energy/media";
        attribute functionLevel : Integer = 2;
        attribute category : String = "PHYSICAL_TRANSFORMATION";
        attribute allocatedProductCode : String = "3100";
    }
    action def FN_F_3110_01 {
        attribute functionId : String = "F-3110-01";
        attribute chineseName : String = "传递能量/介质、耗散能量";
        attribute englishName : String = "Transport energy/media; Dissipate energy";
        attribute functionLevel : Integer = 3;
        attribute category : String = "PHYSICAL_TRANSFORMATION";
        attribute allocatedProductCode : String = "3110";
    }
    action def FN_F_3111_01 {
        attribute functionId : String = "F-3111-01";
        attribute chineseName : String = "通过车轮耗散能量";
        attribute englishName : String = "Dissipate energy through Product 3111";
        attribute functionLevel : Integer = 4;
        attribute category : String = "ENERGY_DISSIPATION";
        attribute allocatedProductCode : String = "3111";
        inout item used_ITM_PHY_005 : I_ITM_PHY_005;
        inout item used_ITM_PHY_006 : I_ITM_PHY_006;
    }
    action def FN_F_3112_01 {
        attribute functionId : String = "F-3112-01";
        attribute chineseName : String = "传递车轴机械能";
        attribute englishName : String = "Transmit mechanical energy through Product 3112";
        attribute functionLevel : Integer = 4;
        attribute category : String = "PHYSICAL_TRANSPORT";
        attribute allocatedProductCode : String = "3112";
        inout item used_ITM_PHY_005 : I_ITM_PHY_005;
    }
    action def FN_F_3120_01 {
        attribute functionId : String = "F-3120-01";
        attribute chineseName : String = "转换能量/物理量";
        attribute englishName : String = "Convert energy/quantities";
        attribute functionLevel : Integer = 3;
        attribute category : String = "PHYSICAL_TRANSFORMATION";
        attribute allocatedProductCode : String = "3120";
    }
    action def FN_F_3121_01 {
        attribute functionId : String = "F-3121-01";
        attribute chineseName : String = "转换齿轮箱主体机械参数";
        attribute englishName : String = "Transform mechanical parameters through Product 3121";
        attribute functionLevel : Integer = 4;
        attribute category : String = "PHYSICAL_TRANSFORMATION";
        attribute allocatedProductCode : String = "3121";
        inout item used_ITM_PHY_005 : I_ITM_PHY_005;
    }
    action def FN_F_3130_01 {
        attribute functionId : String = "F-3130-01";
        attribute chineseName : String = "耗散能量";
        attribute englishName : String = "Dissipate energy";
        attribute functionLevel : Integer = 3;
        attribute category : String = "PHYSICAL_TRANSFORMATION";
        attribute allocatedProductCode : String = "3130";
    }
    action def FN_F_3131_01 {
        attribute functionId : String = "F-3131-01";
        attribute chineseName : String = "通过外轮盘耗散机械制动能量";
        attribute englishName : String = "Dissipate mechanical braking energy through the selected outer wheel disc";
        attribute functionLevel : Integer = 4;
        attribute category : String = "ENERGY_DISSIPATION";
        attribute allocatedProductCode : String = "3131";
        inout item used_ITM_PHY_007 : I_ITM_PHY_007;
        inout item used_ITM_PHY_013 : I_ITM_PHY_013;
    }
    action def FN_F_3132_01 {
        attribute functionId : String = "F-3132-01";
        attribute chineseName : String = "通过内轮盘耗散能量";
        attribute englishName : String = "Dissipate energy through Product 3132";
        attribute functionLevel : Integer = 4;
        attribute category : String = "ENERGY_DISSIPATION";
        attribute allocatedProductCode : String = "3132";
        inout item used_ITM_PHY_007 : I_ITM_PHY_007;
        inout item used_ITM_PHY_013 : I_ITM_PHY_013;
    }
    action def FN_F_3133_01 {
        attribute functionId : String = "F-3133-01";
        attribute chineseName : String = "通过轴盘耗散能量";
        attribute englishName : String = "Dissipate energy through Product 3133";
        attribute functionLevel : Integer = 4;
        attribute category : String = "ENERGY_DISSIPATION";
        attribute allocatedProductCode : String = "3133";
        inout item used_ITM_PHY_013 : I_ITM_PHY_013;
        inout item used_ITM_PHY_007 : I_ITM_PHY_007;
    }
    action def FN_F_3500_01 {
        attribute functionId : String = "F-3500-01";
        attribute chineseName : String = "传递能量/介质";
        attribute englishName : String = "Transport energy/media";
        attribute functionLevel : Integer = 2;
        attribute category : String = "PHYSICAL_TRANSPORT";
        attribute allocatedProductCode : String = "3500";
    }
    action def FN_F_3510_01 {
        attribute functionId : String = "F-3510-01";
        attribute chineseName : String = "传递能量/介质";
        attribute englishName : String = "Transport energy/media";
        attribute functionLevel : Integer = 3;
        attribute category : String = "PHYSICAL_TRANSPORT";
        attribute allocatedProductCode : String = "3510";
    }
    action def FN_F_3511_01 {
        attribute functionId : String = "F-3511-01";
        attribute chineseName : String = "传递联轴节(电机侧)机械能";
        attribute englishName : String = "Transmit mechanical energy through Product 3511";
        attribute functionLevel : Integer = 4;
        attribute category : String = "PHYSICAL_TRANSPORT";
        attribute allocatedProductCode : String = "3511";
        inout item used_ITM_PHY_005 : I_ITM_PHY_005;
    }
    action def FN_F_3512_01 {
        attribute functionId : String = "F-3512-01";
        attribute chineseName : String = "传递联轴节(齿轮箱侧)机械能";
        attribute englishName : String = "Transmit mechanical energy through Product 3512";
        attribute functionLevel : Integer = 4;
        attribute category : String = "PHYSICAL_TRANSPORT";
        attribute allocatedProductCode : String = "3512";
        inout item used_ITM_PHY_005 : I_ITM_PHY_005;
    }
    action def FN_F_3514_01 {
        attribute functionId : String = "F-3514-01";
        attribute chineseName : String = "传递万向轴机械能";
        attribute englishName : String = "Transmit mechanical energy through Product 3514";
        attribute functionLevel : Integer = 4;
        attribute category : String = "PHYSICAL_TRANSPORT";
        attribute allocatedProductCode : String = "3514";
        inout item used_ITM_PHY_005 : I_ITM_PHY_005;
    }
    action def FN_F_3600_01 {
        attribute functionId : String = "F-3600-01";
        attribute chineseName : String = "检测运行参数";
        attribute englishName : String = "Measure parameters";
        attribute functionLevel : Integer = 2;
        attribute category : String = "PHYSICAL_TRANSPORT";
        attribute allocatedProductCode : String = "3600";
    }
    action def FN_F_3640_01 {
        attribute functionId : String = "F-3640-01";
        attribute chineseName : String = "检测运行参数";
        attribute englishName : String = "Measure parameters";
        attribute functionLevel : Integer = 3;
        attribute category : String = "PHYSICAL_TRANSPORT";
        attribute allocatedProductCode : String = "3640";
    }
    action def FN_F_3641_01 {
        attribute functionId : String = "F-3641-01";
        attribute chineseName : String = "检测轴端速度传感器状态";
        attribute englishName : String = "Measure state at Product 3641";
        attribute functionLevel : Integer = 4;
        attribute category : String = "MEASUREMENT";
        attribute allocatedProductCode : String = "3641";
        inout item used_ITM_PHY_005 : I_ITM_PHY_005;
        out item used_ITM_MEA_002 : I_ITM_MEA_002;
    }
    action def FN_F_3643_01 {
        attribute functionId : String = "F-3643-01";
        attribute chineseName : String = "检测齿轮箱速度传感器状态";
        attribute englishName : String = "Measure state at Product 3643";
        attribute functionLevel : Integer = 4;
        attribute category : String = "MEASUREMENT";
        attribute allocatedProductCode : String = "3643";
        out item used_ITM_MEA_003 : I_ITM_MEA_003;
        inout item used_ITM_PHY_005 : I_ITM_PHY_005;
    }
    action def FN_F_3644_01 {
        attribute functionId : String = "F-3644-01";
        attribute chineseName : String = "检测牵引电机速度传感器状态";
        attribute englishName : String = "Measure state at Product 3644";
        attribute functionLevel : Integer = 4;
        attribute category : String = "MEASUREMENT";
        attribute allocatedProductCode : String = "3644";
        out item used_ITM_MEA_004 : I_ITM_MEA_004;
        inout item used_ITM_PHY_005 : I_ITM_PHY_005;
    }
    action def FN_F_3800_01 {
        attribute functionId : String = "F-3800-01";
        attribute chineseName : String = "转换能量/物理量、控制运行";
        attribute englishName : String = "Convert energy/quantities; Control operation";
        attribute functionLevel : Integer = 2;
        attribute category : String = "COORDINATION";
        attribute allocatedProductCode : String = "3800";
    }
    action def FN_F_3810_01 {
        attribute functionId : String = "F-3810-01";
        attribute chineseName : String = "转换能量/物理量、控制运行";
        attribute englishName : String = "Convert energy/quantities; Control operation";
        attribute functionLevel : Integer = 3;
        attribute category : String = "COORDINATION";
        attribute allocatedProductCode : String = "3810";
    }
    action def FN_F_3811_01 {
        attribute functionId : String = "F-3811-01";
        attribute chineseName : String = "控制撒砂控制单元运行";
        attribute englishName : String = "Control Product 3811 operation";
        attribute functionLevel : Integer = 4;
        attribute category : String = "CONTROL";
        attribute allocatedProductCode : String = "3811";
        in item used_ITM_CMD_024 : I_ITM_CMD_024;
        out item used_ITM_CMD_032 : I_ITM_CMD_032;
    }
    action def FN_F_3811_02 {
        attribute functionId : String = "F-3811-02";
        attribute chineseName : String = "报告撒砂控制单元运行状态";
        attribute englishName : String = "Report Product 3811 operating state";
        attribute functionLevel : Integer = 4;
        attribute category : String = "STATUS_REPORTING";
        attribute allocatedProductCode : String = "3811";
        out item used_ITM_STA_012 : I_ITM_STA_012;
    }
    action def FN_F_3813_01 {
        attribute functionId : String = "F-3813-01";
        attribute chineseName : String = "执行撒砂阀板组件动作";
        attribute englishName : String = "Execute Product 3813 action";
        attribute functionLevel : Integer = 4;
        attribute category : String = "PHYSICAL_TRANSFORMATION";
        attribute allocatedProductCode : String = "3813";
        out item used_ITM_STA_012 : I_ITM_STA_012;
        in item used_ITM_CMD_032 : I_ITM_CMD_032;
        inout item used_ITM_PHY_012 : I_ITM_PHY_012;
        inout item used_ITM_PHY_008 : I_ITM_PHY_008;
    }
    action def FN_F_3814_01 {
        attribute functionId : String = "F-3814-01";
        attribute chineseName : String = "执行撒砂喷嘴组件动作";
        attribute englishName : String = "Execute Product 3814 action";
        attribute functionLevel : Integer = 4;
        attribute category : String = "PHYSICAL_TRANSFORMATION";
        attribute allocatedProductCode : String = "3814";
        inout item used_ITM_PHY_012 : I_ITM_PHY_012;
    }
    action def FN_F_4000_01 {
        attribute functionId : String = "F-4000-01";
        attribute chineseName : String = "转换能量/物理量、控制运行";
        attribute englishName : String = "Convert energy/quantities; Control operation";
        attribute functionLevel : Integer = 1;
        attribute category : String = "COORDINATION";
        attribute allocatedProductCode : String = "4000";
    }
    action def FN_F_4100_01 {
        attribute functionId : String = "F-4100-01";
        attribute chineseName : String = "传递能量/介质、控制运行";
        attribute englishName : String = "Transport energy/media; Control operation";
        attribute functionLevel : Integer = 2;
        attribute category : String = "COORDINATION";
        attribute allocatedProductCode : String = "4100";
    }
    action def FN_F_4110_01 {
        attribute functionId : String = "F-4110-01";
        attribute chineseName : String = "传递能量/介质、控制运行";
        attribute englishName : String = "Transport energy/media; Control operation";
        attribute functionLevel : Integer = 3;
        attribute category : String = "COORDINATION";
        attribute allocatedProductCode : String = "4110";
    }
    action def FN_F_4111_01 {
        attribute functionId : String = "F-4111-01";
        attribute chineseName : String = "传递碳滑板电能";
        attribute englishName : String = "Transmit electrical energy through Product 4111";
        attribute functionLevel : Integer = 4;
        attribute category : String = "PHYSICAL_TRANSPORT";
        attribute allocatedProductCode : String = "4111";
        inout item used_ITM_PHY_001 : I_ITM_PHY_001;
    }
    action def FN_F_411C_01 {
        attribute functionId : String = "F-411C-01";
        attribute chineseName : String = "控制受电弓电子控制单元运行";
        attribute englishName : String = "Control Product 411C operation";
        attribute functionLevel : Integer = 4;
        attribute category : String = "CONTROL";
        attribute allocatedProductCode : String = "411C";
        in item used_ITM_CMD_018 : I_ITM_CMD_018;
    }
    action def FN_F_411C_02 {
        attribute functionId : String = "F-411C-02";
        attribute chineseName : String = "报告受电弓电子控制单元运行状态";
        attribute englishName : String = "Report Product 411C operating state";
        attribute functionLevel : Integer = 4;
        attribute category : String = "STATUS_REPORTING";
        attribute allocatedProductCode : String = "411C";
        out item used_ITM_STA_016 : I_ITM_STA_016;
        out item used_ITM_STA_015 : I_ITM_STA_015;
    }
    action def FN_F_4200_01 {
        attribute functionId : String = "F-4200-01";
        attribute chineseName : String = "传递能量/介质、控制运行";
        attribute englishName : String = "Transport energy/media; Control operation";
        attribute functionLevel : Integer = 2;
        attribute category : String = "COORDINATION";
        attribute allocatedProductCode : String = "4200";
    }
    action def FN_F_4210_01 {
        attribute functionId : String = "F-4210-01";
        attribute chineseName : String = "传递能量/介质";
        attribute englishName : String = "Transport energy/media";
        attribute functionLevel : Integer = 3;
        attribute category : String = "PHYSICAL_TRANSPORT";
        attribute allocatedProductCode : String = "4210";
    }
    action def FN_F_4211_01 {
        attribute functionId : String = "F-4211-01";
        attribute chineseName : String = "传递真空断路器电能";
        attribute englishName : String = "Transmit electrical energy through Product 4211";
        attribute functionLevel : Integer = 4;
        attribute category : String = "PHYSICAL_TRANSPORT";
        attribute allocatedProductCode : String = "4211";
        inout item used_ITM_PHY_001 : I_ITM_PHY_001;
    }
    action def FN_F_4212_01 {
        attribute functionId : String = "F-4212-01";
        attribute chineseName : String = "传递非真空隔离开关电能";
        attribute englishName : String = "Transmit electrical energy through Product 4212";
        attribute functionLevel : Integer = 4;
        attribute category : String = "PHYSICAL_TRANSPORT";
        attribute allocatedProductCode : String = "4212";
        inout item used_ITM_PHY_001 : I_ITM_PHY_001;
    }
    action def FN_F_4230_01 {
        attribute functionId : String = "F-4230-01";
        attribute chineseName : String = "控制运行、检测运行参数";
        attribute englishName : String = "Control operation; Measure parameters";
        attribute functionLevel : Integer = 3;
        attribute category : String = "COORDINATION";
        attribute allocatedProductCode : String = "4230";
    }
    action def FN_F_4235_01 {
        attribute functionId : String = "F-4235-01";
        attribute chineseName : String = "检测高压电压互感器状态";
        attribute englishName : String = "Measure state at Product 4235";
        attribute functionLevel : Integer = 4;
        attribute category : String = "MEASUREMENT";
        attribute allocatedProductCode : String = "4235";
        out item used_ITM_MEA_005 : I_ITM_MEA_005;
        inout item used_ITM_PHY_001 : I_ITM_PHY_001;
    }
    action def FN_F_4236_01 {
        attribute functionId : String = "F-4236-01";
        attribute chineseName : String = "检测并贯通高压电流互感器物理量";
        attribute englishName : String = "Measure while conducting the physical quantity through Product 4236";
        attribute functionLevel : Integer = 4;
        attribute category : String = "MEASUREMENT";
        attribute allocatedProductCode : String = "4236";
        inout item used_ITM_PHY_001 : I_ITM_PHY_001;
        out item used_ITM_MEA_006 : I_ITM_MEA_006;
    }
    action def FN_F_4238_01 {
        attribute functionId : String = "F-4238-01";
        attribute chineseName : String = "路由高压控制输入输出单元输入输出信号";
        attribute englishName : String = "Route input and output signals through Product 4238";
        attribute functionLevel : Integer = 4;
        attribute category : String = "CONTROL";
        attribute allocatedProductCode : String = "4238";
        in item used_ITM_CMD_018 : I_ITM_CMD_018;
        out item used_ITM_CMD_016 : I_ITM_CMD_016;
        out item used_ITM_MEA_005 : I_ITM_MEA_005;
        out item used_ITM_MEA_006 : I_ITM_MEA_006;
        in item used_ITM_CMD_017 : I_ITM_CMD_017;
    }
    action def FN_F_4238_02 {
        attribute functionId : String = "F-4238-02";
        attribute chineseName : String = "协调高压控制输入输出单元接口交互";
        attribute englishName : String = "Coordinate Product 4238 interface interactions";
        attribute functionLevel : Integer = 4;
        attribute category : String = "COORDINATION";
        attribute allocatedProductCode : String = "4238";
        in item used_ITM_CMD_018 : I_ITM_CMD_018;
    }
    action def FN_F_4238_03 {
        attribute functionId : String = "F-4238-03";
        attribute chineseName : String = "报告高压控制输入输出单元运行状态";
        attribute englishName : String = "Report Product 4238 operating state";
        attribute functionLevel : Integer = 4;
        attribute category : String = "STATUS_REPORTING";
        attribute allocatedProductCode : String = "4238";
        out item used_ITM_STA_016 : I_ITM_STA_016;
        in item used_ITM_STA_015 : I_ITM_STA_015;
        in item used_ITM_STA_014 : I_ITM_STA_014;
        in item used_ITM_STA_013 : I_ITM_STA_013;
    }
    action def FN_F_4239_01 {
        attribute functionId : String = "F-4239-01";
        attribute chineseName : String = "控制高压控制单元运行";
        attribute englishName : String = "Control Product 4239 operation";
        attribute functionLevel : Integer = 4;
        attribute category : String = "CONTROL";
        attribute allocatedProductCode : String = "4239";
        in item used_ITM_MEA_007 : I_ITM_MEA_007;
        out item used_ITM_CMD_017 : I_ITM_CMD_017;
        out item used_ITM_CMD_018 : I_ITM_CMD_018;
        out item used_ITM_CMD_016 : I_ITM_CMD_016;
        in item used_ITM_MEA_006 : I_ITM_MEA_006;
        in item used_ITM_MEA_005 : I_ITM_MEA_005;
    }
    action def FN_F_4239_02 {
        attribute functionId : String = "F-4239-02";
        attribute chineseName : String = "协调高压控制单元接口交互";
        attribute englishName : String = "Coordinate Product 4239 interface interactions";
        attribute functionLevel : Integer = 4;
        attribute category : String = "COORDINATION";
        attribute allocatedProductCode : String = "4239";
        out item used_ITM_CMD_018 : I_ITM_CMD_018;
    }
    action def FN_F_4239_03 {
        attribute functionId : String = "F-4239-03";
        attribute chineseName : String = "报告高压控制单元运行状态";
        attribute englishName : String = "Report Product 4239 operating state";
        attribute functionLevel : Integer = 4;
        attribute category : String = "STATUS_REPORTING";
        attribute allocatedProductCode : String = "4239";
        in item used_ITM_STA_013 : I_ITM_STA_013;
        in item used_ITM_STA_014 : I_ITM_STA_014;
        in item used_ITM_STA_016 : I_ITM_STA_016;
        in item used_ITM_STA_015 : I_ITM_STA_015;
        in item used_ITM_STA_024 : I_ITM_STA_024;
    }
    action def FN_F_4240_01 {
        attribute functionId : String = "F-4240-01";
        attribute chineseName : String = "控制运行、反馈运行状态";
        attribute englishName : String = "Control operation; Report status";
        attribute functionLevel : Integer = 3;
        attribute category : String = "COORDINATION";
        attribute allocatedProductCode : String = "4240";
    }
    action def FN_F_4241_01 {
        attribute functionId : String = "F-4241-01";
        attribute chineseName : String = "控制处理单元运行";
        attribute englishName : String = "Control Product 4241 operation";
        attribute functionLevel : Integer = 4;
        attribute category : String = "CONTROL";
        attribute allocatedProductCode : String = "4241";
        in item used_ITM_MEA_005 : I_ITM_MEA_005;
        in item used_ITM_MEA_006 : I_ITM_MEA_006;
    }
    action def FN_F_4241_02 {
        attribute functionId : String = "F-4241-02";
        attribute chineseName : String = "报告处理单元运行状态";
        attribute englishName : String = "Report Product 4241 operating state";
        attribute functionLevel : Integer = 4;
        attribute category : String = "STATUS_REPORTING";
        attribute allocatedProductCode : String = "4241";
        out item used_ITM_STA_035 : I_ITM_STA_035;
    }
    action def FN_F_4241_03 {
        attribute functionId : String = "F-4241-03";
        attribute chineseName : String = "统计处理单元运行数据";
        attribute englishName : String = "Accumulate Product 4241 operating statistics";
        attribute functionLevel : Integer = 4;
        attribute category : String = "STATISTICS";
        attribute allocatedProductCode : String = "4241";
        out item used_ITM_ACC_007 : I_ITM_ACC_007;
        out item used_ITM_ACC_009 : I_ITM_ACC_009;
        out item used_ITM_ACC_001 : I_ITM_ACC_001;
        out item used_ITM_ACC_003 : I_ITM_ACC_003;
    }
    action def FN_F_4400_01 {
        attribute functionId : String = "F-4400-01";
        attribute chineseName : String = "传递能量/介质";
        attribute englishName : String = "Transport energy/media";
        attribute functionLevel : Integer = 2;
        attribute category : String = "PHYSICAL_TRANSPORT";
        attribute allocatedProductCode : String = "4400";
    }
    action def FN_F_4410_01 {
        attribute functionId : String = "F-4410-01";
        attribute chineseName : String = "传递能量/介质";
        attribute englishName : String = "Transport energy/media";
        attribute functionLevel : Integer = 3;
        attribute category : String = "PHYSICAL_TRANSPORT";
        attribute allocatedProductCode : String = "4410";
    }
    action def FN_F_4411_01 {
        attribute functionId : String = "F-4411-01";
        attribute chineseName : String = "传递接地变压器物理能量";
        attribute englishName : String = "Transmit physical energy through Product 4411";
        attribute functionLevel : Integer = 4;
        attribute category : String = "PHYSICAL_TRANSPORT";
        attribute allocatedProductCode : String = "4411";
        inout item used_ITM_PHY_013 : I_ITM_PHY_013;
        inout item used_ITM_PHY_011 : I_ITM_PHY_011;
    }
    action def FN_F_4412_01 {
        attribute functionId : String = "F-4412-01";
        attribute chineseName : String = "传递主回路接地电阻物理能量";
        attribute englishName : String = "Transmit physical energy through Product 4412";
        attribute functionLevel : Integer = 4;
        attribute category : String = "PHYSICAL_TRANSPORT";
        attribute allocatedProductCode : String = "4412";
        inout item used_ITM_PHY_013 : I_ITM_PHY_013;
        inout item used_ITM_PHY_011 : I_ITM_PHY_011;
    }
    action def FN_F_4413_01 {
        attribute functionId : String = "F-4413-01";
        attribute chineseName : String = "传递回流碳刷电能";
        attribute englishName : String = "Transmit electrical energy through Product 4413";
        attribute functionLevel : Integer = 4;
        attribute category : String = "PHYSICAL_TRANSPORT";
        attribute allocatedProductCode : String = "4413";
        inout item used_ITM_PHY_011 : I_ITM_PHY_011;
    }
    action def FN_F_4500_01 {
        attribute functionId : String = "F-4500-01";
        attribute chineseName : String = "转换能量/物理量、控制运行";
        attribute englishName : String = "Convert energy/quantities; Control operation";
        attribute functionLevel : Integer = 2;
        attribute category : String = "COORDINATION";
        attribute allocatedProductCode : String = "4500";
    }
    action def FN_F_4510_01 {
        attribute functionId : String = "F-4510-01";
        attribute chineseName : String = "转换能量/物理量、控制运行";
        attribute englishName : String = "Convert energy/quantities; Control operation";
        attribute functionLevel : Integer = 3;
        attribute category : String = "COORDINATION";
        attribute allocatedProductCode : String = "4510";
    }
    action def FN_F_4511_01 {
        attribute functionId : String = "F-4511-01";
        attribute chineseName : String = "实现高压交流电能与牵引变压器次级交流电能转换";
        attribute englishName : String = "Transform high-voltage AC to traction-transformer secondary AC";
        attribute functionLevel : Integer = 4;
        attribute category : String = "PHYSICAL_TRANSFORMATION";
        attribute allocatedProductCode : String = "4511";
        inout item used_ITM_PHY_001 : I_ITM_PHY_001;
        inout item used_ITM_PHY_014 : I_ITM_PHY_014;
    }
    action def FN_F_4513_01 {
        attribute functionId : String = "F-4513-01";
        attribute chineseName : String = "传递电抗器电能";
        attribute englishName : String = "Transmit electrical energy through Product 4513";
        attribute functionLevel : Integer = 4;
        attribute category : String = "PHYSICAL_TRANSPORT";
        attribute allocatedProductCode : String = "4513";
        inout item used_ITM_PHY_014 : I_ITM_PHY_014;
    }
    action def FN_F_4517_01 {
        attribute functionId : String = "F-4517-01";
        attribute chineseName : String = "检测主变压器检测及保护元件状态";
        attribute englishName : String = "Measure state at Product 4517";
        attribute functionLevel : Integer = 4;
        attribute category : String = "MEASUREMENT";
        attribute allocatedProductCode : String = "4517";
        out item used_ITM_MEA_022 : I_ITM_MEA_022;
        out item used_ITM_STA_016 : I_ITM_STA_016;
        inout item used_ITM_PHY_015 : I_ITM_PHY_015;
    }
    action def FN_F_4518_01 {
        attribute functionId : String = "F-4518-01";
        attribute chineseName : String = "控制主变压器控制装置运行";
        attribute englishName : String = "Control Product 4518 operation";
        attribute functionLevel : Integer = 4;
        attribute category : String = "CONTROL";
        attribute allocatedProductCode : String = "4518";
        in item used_ITM_MEA_022 : I_ITM_MEA_022;
        out item used_ITM_CMD_016 : I_ITM_CMD_016;
    }
    action def FN_F_4518_02 {
        attribute functionId : String = "F-4518-02";
        attribute chineseName : String = "报告主变压器控制装置运行状态";
        attribute englishName : String = "Report Product 4518 operating state";
        attribute functionLevel : Integer = 4;
        attribute category : String = "STATUS_REPORTING";
        attribute allocatedProductCode : String = "4518";
        in item used_ITM_STA_016 : I_ITM_STA_016;
        in item used_ITM_STA_013 : I_ITM_STA_013;
    }
    action def FN_F_5000_01 {
        attribute functionId : String = "F-5000-01";
        attribute chineseName : String = "转换能量/物理量、控制运行";
        attribute englishName : String = "Convert energy/quantities; Control operation";
        attribute functionLevel : Integer = 1;
        attribute category : String = "COORDINATION";
        attribute allocatedProductCode : String = "5000";
    }
    action def FN_F_5100_01 {
        attribute functionId : String = "F-5100-01";
        attribute chineseName : String = "转换能量/物理量、控制运行";
        attribute englishName : String = "Convert energy/quantities; Control operation";
        attribute functionLevel : Integer = 2;
        attribute category : String = "COORDINATION";
        attribute allocatedProductCode : String = "5100";
    }
    action def FN_F_5110_01 {
        attribute functionId : String = "F-5110-01";
        attribute chineseName : String = "控制运行、检测运行参数";
        attribute englishName : String = "Control operation; Measure parameters";
        attribute functionLevel : Integer = 3;
        attribute category : String = "COORDINATION";
        attribute allocatedProductCode : String = "5110";
    }
    action def FN_F_5111_01 {
        attribute functionId : String = "F-5111-01";
        attribute chineseName : String = "控制网侧变流器控制模块运行";
        attribute englishName : String = "Control Product 5111 operation";
        attribute functionLevel : Integer = 4;
        attribute category : String = "CONTROL";
        attribute allocatedProductCode : String = "5111";
        in item used_ITM_MEA_008 : I_ITM_MEA_008;
        in item used_ITM_MEA_009 : I_ITM_MEA_009;
        in item used_ITM_MEA_006 : I_ITM_MEA_006;
        out item used_ITM_CMD_010 : I_ITM_CMD_010;
        in item used_ITM_MEA_007 : I_ITM_MEA_007;
        in item used_ITM_MEA_005 : I_ITM_MEA_005;
    }
    action def FN_F_5111_02 {
        attribute functionId : String = "F-5111-02";
        attribute chineseName : String = "协调网侧变流器控制模块接口交互";
        attribute englishName : String = "Coordinate Product 5111 interface interactions";
        attribute functionLevel : Integer = 4;
        attribute category : String = "COORDINATION";
        attribute allocatedProductCode : String = "5111";
        in item used_ITM_MEA_008 : I_ITM_MEA_008;
    }
    action def FN_F_5111_03 {
        attribute functionId : String = "F-5111-03";
        attribute chineseName : String = "限制并保护网侧变流器控制模块运行";
        attribute englishName : String = "Limit and protect Product 5111 operation";
        attribute functionLevel : Integer = 4;
        attribute category : String = "PROTECTION";
        attribute allocatedProductCode : String = "5111";
        out item used_ITM_LIM_005 : I_ITM_LIM_005;
        out item used_ITM_LIM_004 : I_ITM_LIM_004;
    }
    action def FN_F_5111_04 {
        attribute functionId : String = "F-5111-04";
        attribute chineseName : String = "报告网侧变流器控制模块运行状态";
        attribute englishName : String = "Report Product 5111 operating state";
        attribute functionLevel : Integer = 4;
        attribute category : String = "STATUS_REPORTING";
        attribute allocatedProductCode : String = "5111";
        out item used_ITM_STA_019 : I_ITM_STA_019;
        out item used_ITM_STA_017 : I_ITM_STA_017;
    }
    action def FN_F_5112_01 {
        attribute functionId : String = "F-5112-01";
        attribute chineseName : String = "控制电机侧变流器控制模块运行";
        attribute englishName : String = "Control Product 5112 operation";
        attribute functionLevel : Integer = 4;
        attribute category : String = "CONTROL";
        attribute allocatedProductCode : String = "5112";
        out item used_ITM_CMD_011 : I_ITM_CMD_011;
        in item used_ITM_MEA_008 : I_ITM_MEA_008;
        in item used_ITM_MEA_011 : I_ITM_MEA_011;
        in item used_ITM_MEA_009 : I_ITM_MEA_009;
        in item used_ITM_MEA_012 : I_ITM_MEA_012;
        in item used_ITM_MEA_010 : I_ITM_MEA_010;
        in item used_ITM_CMD_012 : I_ITM_CMD_012;
        in item used_ITM_MEA_004 : I_ITM_MEA_004;
    }
    action def FN_F_5112_02 {
        attribute functionId : String = "F-5112-02";
        attribute chineseName : String = "协调电机侧变流器控制模块接口交互";
        attribute englishName : String = "Coordinate Product 5112 interface interactions";
        attribute functionLevel : Integer = 4;
        attribute category : String = "COORDINATION";
        attribute allocatedProductCode : String = "5112";
        in item used_ITM_MEA_008 : I_ITM_MEA_008;
    }
    action def FN_F_5112_03 {
        attribute functionId : String = "F-5112-03";
        attribute chineseName : String = "限制并保护电机侧变流器控制模块运行";
        attribute englishName : String = "Limit and protect Product 5112 operation";
        attribute functionLevel : Integer = 4;
        attribute category : String = "PROTECTION";
        attribute allocatedProductCode : String = "5112";
        out item used_ITM_LIM_003 : I_ITM_LIM_003;
        out item used_ITM_LIM_001 : I_ITM_LIM_001;
        out item used_ITM_LIM_004 : I_ITM_LIM_004;
    }
    action def FN_F_5112_04 {
        attribute functionId : String = "F-5112-04";
        attribute chineseName : String = "报告电机侧变流器控制模块运行状态";
        attribute englishName : String = "Report Product 5112 operating state";
        attribute functionLevel : Integer = 4;
        attribute category : String = "STATUS_REPORTING";
        attribute allocatedProductCode : String = "5112";
        out item used_ITM_STA_002 : I_ITM_STA_002;
        out item used_ITM_STA_001 : I_ITM_STA_001;
        out item used_ITM_STA_019 : I_ITM_STA_019;
        out item used_ITM_STA_018 : I_ITM_STA_018;
    }
    action def FN_F_5113_01 {
        attribute functionId : String = "F-5113-01";
        attribute chineseName : String = "检测变流器检测保护组件状态";
        attribute englishName : String = "Measure state at Product 5113";
        attribute functionLevel : Integer = 4;
        attribute category : String = "MEASUREMENT";
        attribute allocatedProductCode : String = "5113";
        inout item used_ITM_PHY_015 : I_ITM_PHY_015;
        out item used_ITM_MEA_023 : I_ITM_MEA_023;
        out item used_ITM_MEA_009 : I_ITM_MEA_009;
        out item used_ITM_STA_019 : I_ITM_STA_019;
        out item used_ITM_STA_020 : I_ITM_STA_020;
        out item used_ITM_LIM_007 : I_ITM_LIM_007;
        out item used_ITM_MEA_010 : I_ITM_MEA_010;
        out item used_ITM_MEA_008 : I_ITM_MEA_008;
    }
    action def FN_F_5120_01 {
        attribute functionId : String = "F-5120-01";
        attribute chineseName : String = "传递能量/介质";
        attribute englishName : String = "Transport energy/media";
        attribute functionLevel : Integer = 3;
        attribute category : String = "PHYSICAL_TRANSPORT";
        attribute allocatedProductCode : String = "5120";
    }
    action def FN_F_5121_01 {
        attribute functionId : String = "F-5121-01";
        attribute chineseName : String = "传递预充电组件电能";
        attribute englishName : String = "Transmit electrical energy through Product 5121";
        attribute functionLevel : Integer = 4;
        attribute category : String = "PHYSICAL_TRANSPORT";
        attribute allocatedProductCode : String = "5121";
        inout item used_ITM_PHY_003 : I_ITM_PHY_003;
        inout item used_ITM_PHY_014 : I_ITM_PHY_014;
    }
    action def FN_F_5122_01 {
        attribute functionId : String = "F-5122-01";
        attribute chineseName : String = "传递输入组件电能";
        attribute englishName : String = "Transmit electrical energy through Product 5122";
        attribute functionLevel : Integer = 4;
        attribute category : String = "PHYSICAL_TRANSPORT";
        attribute allocatedProductCode : String = "5122";
        inout item used_ITM_PHY_014 : I_ITM_PHY_014;
        inout item used_ITM_PHY_003 : I_ITM_PHY_003;
    }
    action def FN_F_5130_01 {
        attribute functionId : String = "F-5130-01";
        attribute chineseName : String = "转换能量/物理量、控制运行";
        attribute englishName : String = "Convert energy/quantities; Control operation";
        attribute functionLevel : Integer = 3;
        attribute category : String = "COORDINATION";
        attribute allocatedProductCode : String = "5130";
    }
    action def FN_F_5131_01 {
        attribute functionId : String = "F-5131-01";
        attribute chineseName : String = "实现主变次级交流电能与中间直流电能双向转换";
        attribute englishName : String = "Convert transformer secondary AC and DC-link energy bidirectionally";
        attribute functionLevel : Integer = 4;
        attribute category : String = "PHYSICAL_TRANSFORMATION";
        attribute allocatedProductCode : String = "5131";
        inout item used_ITM_PHY_003 : I_ITM_PHY_003;
        inout item used_ITM_PHY_014 : I_ITM_PHY_014;
    }
    action def FN_F_5131_02 {
        attribute functionId : String = "F-5131-02";
        attribute chineseName : String = "执行网侧变流控制并反馈运行状态";
        attribute englishName : String = "Execute line-side conversion control and report operating state";
        attribute functionLevel : Integer = 4;
        attribute category : String = "CONTROL";
        attribute allocatedProductCode : String = "5131";
        out item used_ITM_MEA_006 : I_ITM_MEA_006;
        out item used_ITM_MEA_009 : I_ITM_MEA_009;
        in item used_ITM_CMD_010 : I_ITM_CMD_010;
        out item used_ITM_MEA_008 : I_ITM_MEA_008;
        out item used_ITM_MEA_005 : I_ITM_MEA_005;
    }
    action def FN_F_5132_01 {
        attribute functionId : String = "F-5132-01";
        attribute chineseName : String = "实现中间直流电能与电机侧三相交流电能双向转换";
        attribute englishName : String = "Convert DC-link and motor-side three-phase AC energy bidirectionally";
        attribute functionLevel : Integer = 4;
        attribute category : String = "PHYSICAL_TRANSFORMATION";
        attribute allocatedProductCode : String = "5132";
        inout item used_ITM_PHY_003 : I_ITM_PHY_003;
        inout item used_ITM_PHY_004 : I_ITM_PHY_004;
    }
    action def FN_F_5132_02 {
        attribute functionId : String = "F-5132-02";
        attribute chineseName : String = "响应电机侧变流控制并反馈运行状态";
        attribute englishName : String = "Execute motor-side conversion control and report operating state";
        attribute functionLevel : Integer = 4;
        attribute category : String = "CONTROL";
        attribute allocatedProductCode : String = "5132";
        in item used_ITM_CMD_011 : I_ITM_CMD_011;
        out item used_ITM_MEA_011 : I_ITM_MEA_011;
        out item used_ITM_MEA_009 : I_ITM_MEA_009;
        out item used_ITM_MEA_010 : I_ITM_MEA_010;
        out item used_ITM_MEA_008 : I_ITM_MEA_008;
    }
    action def FN_F_5133_01 {
        attribute functionId : String = "F-5133-01";
        attribute chineseName : String = "控制放电电阻控制模块运行";
        attribute englishName : String = "Control Product 5133 operation";
        attribute functionLevel : Integer = 4;
        attribute category : String = "CONTROL";
        attribute allocatedProductCode : String = "5133";
        in item used_ITM_CMD_015 : I_ITM_CMD_015;
        in item used_ITM_MEA_008 : I_ITM_MEA_008;
    }
    action def FN_F_5133_02 {
        attribute functionId : String = "F-5133-02";
        attribute chineseName : String = "限制并保护放电电阻控制模块运行";
        attribute englishName : String = "Limit and protect Product 5133 operation";
        attribute functionLevel : Integer = 4;
        attribute category : String = "PROTECTION";
        attribute allocatedProductCode : String = "5133";
        out item used_ITM_LIM_006 : I_ITM_LIM_006;
    }
    action def FN_F_5133_03 {
        attribute functionId : String = "F-5133-03";
        attribute chineseName : String = "报告放电电阻控制模块运行状态";
        attribute englishName : String = "Report Product 5133 operating state";
        attribute functionLevel : Integer = 4;
        attribute category : String = "STATUS_REPORTING";
        attribute allocatedProductCode : String = "5133";
        out item used_ITM_STA_023 : I_ITM_STA_023;
    }
    action def FN_F_5140_01 {
        attribute functionId : String = "F-5140-01";
        attribute chineseName : String = "耗散能量、检测运行参数";
        attribute englishName : String = "Dissipate energy; Measure parameters";
        attribute functionLevel : Integer = 3;
        attribute category : String = "PHYSICAL_TRANSFORMATION";
        attribute allocatedProductCode : String = "5140";
    }
    action def FN_F_5142_01 {
        attribute functionId : String = "F-5142-01";
        attribute chineseName : String = "通过放电电阻器耗散能量";
        attribute englishName : String = "Dissipate energy through Product 5142";
        attribute functionLevel : Integer = 4;
        attribute category : String = "ENERGY_DISSIPATION";
        attribute allocatedProductCode : String = "5142";
        inout item used_ITM_PHY_003 : I_ITM_PHY_003;
        inout item used_ITM_PHY_013 : I_ITM_PHY_013;
    }
    action def FN_F_5142_02 {
        attribute functionId : String = "F-5142-02";
        attribute chineseName : String = "统计放电电阻器运行数据";
        attribute englishName : String = "Accumulate Product 5142 operating statistics";
        attribute functionLevel : Integer = 4;
        attribute category : String = "STATISTICS";
        attribute allocatedProductCode : String = "5142";
        out item used_ITM_ACC_012 : I_ITM_ACC_012;
        out item used_ITM_ACC_005 : I_ITM_ACC_005;
    }
    action def FN_F_5145_01 {
        attribute functionId : String = "F-5145-01";
        attribute chineseName : String = "检测中间直流环节检测保护组件状态";
        attribute englishName : String = "Measure state at Product 5145";
        attribute functionLevel : Integer = 4;
        attribute category : String = "MEASUREMENT";
        attribute allocatedProductCode : String = "5145";
        out item used_ITM_MEA_008 : I_ITM_MEA_008;
        inout item used_ITM_PHY_015 : I_ITM_PHY_015;
        out item used_ITM_STA_020 : I_ITM_STA_020;
        out item used_ITM_CMD_015 : I_ITM_CMD_015;
        out item used_ITM_LIM_007 : I_ITM_LIM_007;
        out item used_ITM_MEA_009 : I_ITM_MEA_009;
    }
    action def FN_F_5300_01 {
        attribute functionId : String = "F-5300-01";
        attribute chineseName : String = "转换能量/物理量、检测运行参数";
        attribute englishName : String = "Convert energy/quantities; Measure parameters";
        attribute functionLevel : Integer = 2;
        attribute category : String = "PHYSICAL_TRANSFORMATION";
        attribute allocatedProductCode : String = "5300";
    }
    action def FN_F_5310_01 {
        attribute functionId : String = "F-5310-01";
        attribute chineseName : String = "转换能量/物理量、检测运行参数";
        attribute englishName : String = "Convert energy/quantities; Measure parameters";
        attribute functionLevel : Integer = 3;
        attribute category : String = "PHYSICAL_TRANSFORMATION";
        attribute allocatedProductCode : String = "5310";
    }
    action def FN_F_5311_01 {
        attribute functionId : String = "F-5311-01";
        attribute chineseName : String = "实现三相交流电能与旋转机械能双向转换";
        attribute englishName : String = "Convert three-phase AC and rotational mechanical energy bidirectionally";
        attribute functionLevel : Integer = 4;
        attribute category : String = "PHYSICAL_TRANSFORMATION";
        attribute allocatedProductCode : String = "5311";
        inout item used_ITM_PHY_005 : I_ITM_PHY_005;
        inout item used_ITM_PHY_004 : I_ITM_PHY_004;
    }
    action def FN_F_5311_02 {
        attribute functionId : String = "F-5311-02";
        attribute chineseName : String = "提供牵引电机转速、转矩及电气状态反馈";
        attribute englishName : String = "Provide traction-motor speed, torque and electrical feedback";
        attribute functionLevel : Integer = 4;
        attribute category : String = "MEASUREMENT";
        attribute allocatedProductCode : String = "5311";
        out item used_ITM_MEA_011 : I_ITM_MEA_011;
        out item used_ITM_MEA_004 : I_ITM_MEA_004;
        out item used_ITM_MEA_010 : I_ITM_MEA_010;
        out item used_ITM_MEA_012 : I_ITM_MEA_012;
    }
    action def FN_F_7000_01 {
        attribute functionId : String = "F-7000-01";
        attribute chineseName : String = "转换能量/物理量、控制运行";
        attribute englishName : String = "Convert energy/quantities; Control operation";
        attribute functionLevel : Integer = 1;
        attribute category : String = "COORDINATION";
        attribute allocatedProductCode : String = "7000";
    }
    action def FN_F_7100_01 {
        attribute functionId : String = "F-7100-01";
        attribute chineseName : String = "传递能量/介质、检测运行参数";
        attribute englishName : String = "Transport energy/media; Measure parameters";
        attribute functionLevel : Integer = 2;
        attribute category : String = "PHYSICAL_TRANSPORT";
        attribute allocatedProductCode : String = "7100";
    }
    action def FN_F_7120_01 {
        attribute functionId : String = "F-7120-01";
        attribute chineseName : String = "传递能量/介质";
        attribute englishName : String = "Transport energy/media";
        attribute functionLevel : Integer = 3;
        attribute category : String = "PHYSICAL_TRANSPORT";
        attribute allocatedProductCode : String = "7120";
    }
    action def FN_F_7124_01 {
        attribute functionId : String = "F-7124-01";
        attribute chineseName : String = "提供制动风缸外部能量";
        attribute englishName : String = "Provide external energy through Product 7124";
        attribute functionLevel : Integer = 4;
        attribute category : String = "PHYSICAL_TRANSPORT";
        attribute allocatedProductCode : String = "7124";
        inout item used_ITM_PHY_008 : I_ITM_PHY_008;
    }
    action def FN_F_7130_01 {
        attribute functionId : String = "F-7130-01";
        attribute chineseName : String = "传递能量/介质";
        attribute englishName : String = "Transport energy/media";
        attribute functionLevel : Integer = 3;
        attribute category : String = "PHYSICAL_TRANSPORT";
        attribute allocatedProductCode : String = "7130";
    }
    action def FN_F_7131_01 {
        attribute functionId : String = "F-7131-01";
        attribute chineseName : String = "传递总风管气动压力";
        attribute englishName : String = "Transmit pneumatic pressure through Product 7131";
        attribute functionLevel : Integer = 4;
        attribute category : String = "PHYSICAL_TRANSPORT";
        attribute allocatedProductCode : String = "7131";
        inout item used_ITM_PHY_008 : I_ITM_PHY_008;
    }
    action def FN_F_7140_01 {
        attribute functionId : String = "F-7140-01";
        attribute chineseName : String = "检测运行参数";
        attribute englishName : String = "Measure parameters";
        attribute functionLevel : Integer = 3;
        attribute category : String = "PHYSICAL_TRANSPORT";
        attribute allocatedProductCode : String = "7140";
    }
    action def FN_F_7142_01 {
        attribute functionId : String = "F-7142-01";
        attribute chineseName : String = "检测总风管压力传感器状态";
        attribute englishName : String = "Measure state at Product 7142";
        attribute functionLevel : Integer = 4;
        attribute category : String = "MEASUREMENT";
        attribute allocatedProductCode : String = "7142";
        inout item used_ITM_PHY_008 : I_ITM_PHY_008;
        out item used_ITM_MEA_014 : I_ITM_MEA_014;
        out item used_ITM_STA_009 : I_ITM_STA_009;
    }
    action def FN_F_7200_01 {
        attribute functionId : String = "F-7200-01";
        attribute chineseName : String = "转换能量/物理量、控制运行";
        attribute englishName : String = "Convert energy/quantities; Control operation";
        attribute functionLevel : Integer = 2;
        attribute category : String = "COORDINATION";
        attribute allocatedProductCode : String = "7200";
    }
    action def FN_F_7210_01 {
        attribute functionId : String = "F-7210-01";
        attribute chineseName : String = "转换能量/物理量、控制运行";
        attribute englishName : String = "Convert energy/quantities; Control operation";
        attribute functionLevel : Integer = 3;
        attribute category : String = "COORDINATION";
        attribute allocatedProductCode : String = "7210";
    }
    action def FN_F_7211_01 {
        attribute functionId : String = "F-7211-01";
        attribute chineseName : String = "处理制动请求";
        attribute englishName : String = "Process braking requests";
        attribute functionLevel : Integer = 4;
        attribute category : String = "CONTROL";
        attribute allocatedProductCode : String = "7211";
        out item used_ITM_CMD_020 : I_ITM_CMD_020;
        out item used_ITM_CMD_019 : I_ITM_CMD_019;
        in item used_ITM_CMD_003 : I_ITM_CMD_003;
        out item used_ITM_CMD_008 : I_ITM_CMD_008;
        out item used_ITM_CMD_031 : I_ITM_CMD_031;
    }
    action def FN_F_7211_02 {
        attribute functionId : String = "F-7211-02";
        attribute chineseName : String = "协调再生制动与摩擦制动力";
        attribute englishName : String = "Coordinate regenerative and friction braking effort";
        attribute functionLevel : Integer = 4;
        attribute category : String = "COORDINATION";
        attribute allocatedProductCode : String = "7211";
        out item used_ITM_CMD_006 : I_ITM_CMD_006;
        in item used_ITM_MEA_013 : I_ITM_MEA_013;
        in item used_ITM_MEA_001 : I_ITM_MEA_001;
        out item used_ITM_CMD_007 : I_ITM_CMD_007;
        in item used_ITM_MEA_018 : I_ITM_MEA_018;
        in item used_ITM_MEA_021 : I_ITM_MEA_021;
        in item used_ITM_MEA_017 : I_ITM_MEA_017;
        out item used_ITM_LIM_002 : I_ITM_LIM_002;
        in item used_ITM_MEA_014 : I_ITM_MEA_014;
        in item used_ITM_MEA_019 : I_ITM_MEA_019;
        in item used_ITM_MEA_020 : I_ITM_MEA_020;
        in item used_ITM_LIM_001 : I_ITM_LIM_001;
        in item used_ITM_LIM_013 : I_ITM_LIM_013;
        in item used_ITM_MEA_016 : I_ITM_MEA_016;
    }
    action def FN_F_7211_03 {
        attribute functionId : String = "F-7211-03";
        attribute chineseName : String = "执行电空制动控制";
        attribute englishName : String = "Execute electro-pneumatic brake control";
        attribute functionLevel : Integer = 4;
        attribute category : String = "CONTROL";
        attribute allocatedProductCode : String = "7211";
        out item used_ITM_CMD_021 : I_ITM_CMD_021;
        out item used_ITM_CMD_022 : I_ITM_CMD_022;
    }
    action def FN_F_7211_04 {
        attribute functionId : String = "F-7211-04";
        attribute chineseName : String = "协调防滑与紧急制动安全请求";
        attribute englishName : String = "Coordinate anti-slip and emergency-brake safety requests";
        attribute functionLevel : Integer = 4;
        attribute category : String = "SAFETY";
        attribute allocatedProductCode : String = "7211";
        out item used_ITM_STA_006 : I_ITM_STA_006;
        out item used_ITM_STA_007 : I_ITM_STA_007;
        out item used_ITM_STA_010 : I_ITM_STA_010;
        in item used_ITM_STA_009 : I_ITM_STA_009;
        in item used_ITM_STA_025 : I_ITM_STA_025;
        in item used_ITM_LIM_008 : I_ITM_LIM_008;
        in item used_ITM_LIM_014 : I_ITM_LIM_014;
        out item used_ITM_STA_005 : I_ITM_STA_005;
        out item used_ITM_STA_008 : I_ITM_STA_008;
        in item used_ITM_STA_002 : I_ITM_STA_002;
        in item used_ITM_CMD_030 : I_ITM_CMD_030;
        in item used_ITM_CMD_004 : I_ITM_CMD_004;
        out item used_ITM_STA_004 : I_ITM_STA_004;
        out item used_ITM_CMD_023 : I_ITM_CMD_023;
        out item used_ITM_STA_003 : I_ITM_STA_003;
        out item used_ITM_STA_011 : I_ITM_STA_011;
    }
    action def FN_F_7213_01 {
        attribute functionId : String = "F-7213-01";
        attribute chineseName : String = "执行制动控制接触器及其他动作";
        attribute englishName : String = "Execute Product 7213 action";
        attribute functionLevel : Integer = 4;
        attribute category : String = "PHYSICAL_TRANSFORMATION";
        attribute allocatedProductCode : String = "7213";
        out item used_ITM_STA_036 : I_ITM_STA_036;
        inout item used_ITM_PHY_015 : I_ITM_PHY_015;
        in item used_ITM_CMD_031 : I_ITM_CMD_031;
    }
    action def FN_F_7220_01 {
        attribute functionId : String = "F-7220-01";
        attribute chineseName : String = "转换能量/物理量、执行安全控制";
        attribute englishName : String = "Convert energy/quantities; Execute safety control";
        attribute functionLevel : Integer = 3;
        attribute category : String = "SAFETY";
        attribute allocatedProductCode : String = "7220";
    }
    action def FN_F_7222_01 {
        attribute functionId : String = "F-7222-01";
        attribute chineseName : String = "传递电空转换阀气动压力";
        attribute englishName : String = "Transmit pneumatic pressure through Product 7222";
        attribute functionLevel : Integer = 4;
        attribute category : String = "PHYSICAL_TRANSPORT";
        attribute allocatedProductCode : String = "7222";
        inout item used_ITM_PHY_008 : I_ITM_PHY_008;
        inout item used_ITM_PHY_009 : I_ITM_PHY_009;
    }
    action def FN_F_7223_01 {
        attribute functionId : String = "F-7223-01";
        attribute chineseName : String = "传递中继阀气动压力";
        attribute englishName : String = "Transmit pneumatic pressure through Product 7223";
        attribute functionLevel : Integer = 4;
        attribute category : String = "PHYSICAL_TRANSPORT";
        attribute allocatedProductCode : String = "7223";
        inout item used_ITM_PHY_008 : I_ITM_PHY_008;
        inout item used_ITM_PHY_010 : I_ITM_PHY_010;
        inout item used_ITM_PHY_009 : I_ITM_PHY_009;
    }
    action def FN_F_7224_01 {
        attribute functionId : String = "F-7224-01";
        attribute chineseName : String = "检测空重车调整阀状态";
        attribute englishName : String = "Measure state at Product 7224";
        attribute functionLevel : Integer = 4;
        attribute category : String = "MEASUREMENT";
        attribute allocatedProductCode : String = "7224";
        inout item used_ITM_PHY_009 : I_ITM_PHY_009;
        inout item used_ITM_PHY_008 : I_ITM_PHY_008;
        in item used_ITM_MEA_019 : I_ITM_MEA_019;
    }
    action def FN_F_7225_01 {
        attribute functionId : String = "F-7225-01";
        attribute chineseName : String = "执行控制电磁阀动作";
        attribute englishName : String = "Execute Product 7225 action";
        attribute functionLevel : Integer = 4;
        attribute category : String = "PHYSICAL_TRANSFORMATION";
        attribute allocatedProductCode : String = "7225";
        inout item used_ITM_PHY_009 : I_ITM_PHY_009;
        in item used_ITM_CMD_022 : I_ITM_CMD_022;
        inout item used_ITM_PHY_008 : I_ITM_PHY_008;
    }
    action def FN_F_7226_01 {
        attribute functionId : String = "F-7226-01";
        attribute chineseName : String = "执行紧急制动气动隔离与施加";
        attribute englishName : String = "Execute pneumatic isolation and application for emergency braking";
        attribute functionLevel : Integer = 4;
        attribute category : String = "SAFETY";
        attribute allocatedProductCode : String = "7226";
        inout item used_ITM_PHY_008 : I_ITM_PHY_008;
        inout item used_ITM_PHY_009 : I_ITM_PHY_009;
        in item used_ITM_CMD_004 : I_ITM_CMD_004;
        inout item used_ITM_PHY_010 : I_ITM_PHY_010;
        in item used_ITM_CMD_030 : I_ITM_CMD_030;
    }
    action def FN_F_7227_01 {
        attribute functionId : String = "F-7227-01";
        attribute chineseName : String = "执行缓解阀动作";
        attribute englishName : String = "Execute Product 7227 action";
        attribute functionLevel : Integer = 4;
        attribute category : String = "PHYSICAL_TRANSFORMATION";
        attribute allocatedProductCode : String = "7227";
        inout item used_ITM_PHY_010 : I_ITM_PHY_010;
        in item used_ITM_CMD_019 : I_ITM_CMD_019;
    }
    action def FN_F_7228_01 {
        attribute functionId : String = "F-7228-01";
        attribute chineseName : String = "传递车厢直接制动截断塞门气动压力";
        attribute englishName : String = "Transmit pneumatic pressure through Product 7228";
        attribute functionLevel : Integer = 4;
        attribute category : String = "PHYSICAL_TRANSPORT";
        attribute allocatedProductCode : String = "7228";
        inout item used_ITM_PHY_010 : I_ITM_PHY_010;
    }
    action def FN_F_7229_01 {
        attribute functionId : String = "F-7229-01";
        attribute chineseName : String = "传递调压阀气动压力";
        attribute englishName : String = "Transmit pneumatic pressure through Product 7229";
        attribute functionLevel : Integer = 4;
        attribute category : String = "PHYSICAL_TRANSPORT";
        attribute allocatedProductCode : String = "7229";
        inout item used_ITM_PHY_008 : I_ITM_PHY_008;
        inout item used_ITM_PHY_009 : I_ITM_PHY_009;
    }
    action def FN_F_722A_01 {
        attribute functionId : String = "F-722A-01";
        attribute chineseName : String = "传递防滑阀组成气动压力";
        attribute englishName : String = "Transmit pneumatic pressure through Product 722A";
        attribute functionLevel : Integer = 4;
        attribute category : String = "PHYSICAL_TRANSPORT";
        attribute allocatedProductCode : String = "722A";
        inout item used_ITM_PHY_010 : I_ITM_PHY_010;
    }
    action def FN_F_722B_01 {
        attribute functionId : String = "F-722B-01";
        attribute chineseName : String = "检测压力传感器状态";
        attribute englishName : String = "Measure state at Product 722B";
        attribute functionLevel : Integer = 4;
        attribute category : String = "MEASUREMENT";
        attribute allocatedProductCode : String = "722B";
        inout item used_ITM_PHY_010 : I_ITM_PHY_010;
        out item used_ITM_MEA_016 : I_ITM_MEA_016;
    }
    action def FN_F_722C_01 {
        attribute functionId : String = "F-722C-01";
        attribute chineseName : String = "检测压力开关状态";
        attribute englishName : String = "Measure state at Product 722C";
        attribute functionLevel : Integer = 4;
        attribute category : String = "MEASUREMENT";
        attribute allocatedProductCode : String = "722C";
        out item used_ITM_STA_009 : I_ITM_STA_009;
        inout item used_ITM_PHY_010 : I_ITM_PHY_010;
    }
    action def FN_F_7250_01 {
        attribute functionId : String = "F-7250-01";
        attribute chineseName : String = "转换能量/物理量、传递能量/介质";
        attribute englishName : String = "Convert energy/quantities; Transport energy/media";
        attribute functionLevel : Integer = 3;
        attribute category : String = "PHYSICAL_TRANSFORMATION";
        attribute allocatedProductCode : String = "7250";
    }
    action def FN_F_7252_01 {
        attribute functionId : String = "F-7252-01";
        attribute chineseName : String = "传递制动夹钳作用力";
        attribute englishName : String = "Transmit brake-caliper force";
        attribute functionLevel : Integer = 4;
        attribute category : String = "PHYSICAL_TRANSPORT";
        attribute allocatedProductCode : String = "7252";
        inout item used_ITM_PHY_007 : I_ITM_PHY_007;
        inout item used_ITM_PHY_010 : I_ITM_PHY_010;
        out item used_ITM_STA_005 : I_ITM_STA_005;
        out item used_ITM_STA_004 : I_ITM_STA_004;
        out item used_ITM_MEA_017 : I_ITM_MEA_017;
    }
    action def FN_F_7254_01 {
        attribute functionId : String = "F-7254-01";
        attribute chineseName : String = "通过闸片耗散机械制动能量";
        attribute englishName : String = "Dissipate mechanical braking energy through brake pads";
        attribute functionLevel : Integer = 4;
        attribute category : String = "ENERGY_DISSIPATION";
        attribute allocatedProductCode : String = "7254";
        inout item used_ITM_PHY_007 : I_ITM_PHY_007;
        out item used_ITM_ACC_006 : I_ITM_ACC_006;
        out item used_ITM_ACC_013 : I_ITM_ACC_013;
        inout item used_ITM_PHY_013 : I_ITM_PHY_013;
    }
    action def FN_F_7255_01 {
        attribute functionId : String = "F-7255-01";
        attribute chineseName : String = "将气动压力转换为制动机械力";
        attribute englishName : String = "Convert pneumatic pressure into mechanical braking force";
        attribute functionLevel : Integer = 4;
        attribute category : String = "PHYSICAL_TRANSFORMATION";
        attribute allocatedProductCode : String = "7255";
        inout item used_ITM_PHY_007 : I_ITM_PHY_007;
        inout item used_ITM_PHY_010 : I_ITM_PHY_010;
    }
    action def FN_F_7280_01 {
        attribute functionId : String = "F-7280-01";
        attribute chineseName : String = "转换能量/物理量、传递能量/介质";
        attribute englishName : String = "Convert energy/quantities; Transport energy/media";
        attribute functionLevel : Integer = 3;
        attribute category : String = "PHYSICAL_TRANSFORMATION";
        attribute allocatedProductCode : String = "7280";
    }
    action def FN_F_7281_01 {
        attribute functionId : String = "F-7281-01";
        attribute chineseName : String = "执行制动指示器动作";
        attribute englishName : String = "Execute Product 7281 action";
        attribute functionLevel : Integer = 4;
        attribute category : String = "PHYSICAL_TRANSFORMATION";
        attribute allocatedProductCode : String = "7281";
        inout item used_ITM_PHY_015 : I_ITM_PHY_015;
        in item used_ITM_STA_004 : I_ITM_STA_004;
        in item used_ITM_STA_006 : I_ITM_STA_006;
        in item used_ITM_STA_005 : I_ITM_STA_005;
    }
    action def FN_F_7284_01 {
        attribute functionId : String = "F-7284-01";
        attribute chineseName : String = "传递转向架制动截断塞门气动压力";
        attribute englishName : String = "Transmit pneumatic pressure through Product 7284";
        attribute functionLevel : Integer = 4;
        attribute category : String = "PHYSICAL_TRANSPORT";
        attribute allocatedProductCode : String = "7284";
        inout item used_ITM_PHY_010 : I_ITM_PHY_010;
    }
    action def FN_F_7285_01 {
        attribute functionId : String = "F-7285-01";
        attribute chineseName : String = "传递单轴制动截断塞门气动压力";
        attribute englishName : String = "Transmit pneumatic pressure through Product 7285";
        attribute functionLevel : Integer = 4;
        attribute category : String = "PHYSICAL_TRANSPORT";
        attribute allocatedProductCode : String = "7285";
        inout item used_ITM_PHY_010 : I_ITM_PHY_010;
    }
    action def FN_F_8000_01 {
        attribute functionId : String = "F-8000-01";
        attribute chineseName : String = "控制运行、实施保护与限制";
        attribute englishName : String = "Control operation; Protect/limit operation";
        attribute functionLevel : Integer = 1;
        attribute category : String = "COORDINATION";
        attribute allocatedProductCode : String = "8000";
    }
    action def FN_F_8100_01 {
        attribute functionId : String = "F-8100-01";
        attribute chineseName : String = "控制运行、实施保护与限制";
        attribute englishName : String = "Control operation; Protect/limit operation";
        attribute functionLevel : Integer = 2;
        attribute category : String = "COORDINATION";
        attribute allocatedProductCode : String = "8100";
    }
    action def FN_F_8120_01 {
        attribute functionId : String = "F-8120-01";
        attribute chineseName : String = "控制运行、实施保护与限制";
        attribute englishName : String = "Control operation; Protect/limit operation";
        attribute functionLevel : Integer = 3;
        attribute category : String = "COORDINATION";
        attribute allocatedProductCode : String = "8120";
    }
    action def FN_F_8121_01 {
        attribute functionId : String = "F-8121-01";
        attribute chineseName : String = "控制主控制单元运行";
        attribute englishName : String = "Control Product 8121 operation";
        attribute functionLevel : Integer = 4;
        attribute category : String = "CONTROL";
        attribute allocatedProductCode : String = "8121";
        in item used_ITM_CMD_001 : I_ITM_CMD_001;
        in item used_ITM_CMD_002 : I_ITM_CMD_002;
        out item used_ITM_CMD_008 : I_ITM_CMD_008;
        in item used_ITM_CMD_003 : I_ITM_CMD_003;
        out item used_ITM_CMD_004 : I_ITM_CMD_004;
        in item used_ITM_CMD_030 : I_ITM_CMD_030;
        in item used_ITM_MEA_001 : I_ITM_MEA_001;
        out item used_ITM_CMD_009 : I_ITM_CMD_009;
    }
    action def FN_F_8121_02 {
        attribute functionId : String = "F-8121-02";
        attribute chineseName : String = "协调主控制单元接口交互";
        attribute englishName : String = "Coordinate Product 8121 interface interactions";
        attribute functionLevel : Integer = 4;
        attribute category : String = "COORDINATION";
        attribute allocatedProductCode : String = "8121";
        in item used_ITM_STA_027 : I_ITM_STA_027;
    }
    action def FN_F_8121_03 {
        attribute functionId : String = "F-8121-03";
        attribute chineseName : String = "报告主控制单元运行状态";
        attribute englishName : String = "Report Product 8121 operating state";
        attribute functionLevel : Integer = 4;
        attribute category : String = "STATUS_REPORTING";
        attribute allocatedProductCode : String = "8121";
        in item used_ITM_STA_025 : I_ITM_STA_025;
        in item used_ITM_STA_024 : I_ITM_STA_024;
        in item used_ITM_STA_027 : I_ITM_STA_027;
        in item used_ITM_STA_001 : I_ITM_STA_001;
        in item used_ITM_STA_026 : I_ITM_STA_026;
        in item used_ITM_STA_003 : I_ITM_STA_003;
    }
    action def FN_F_8122_01 {
        attribute functionId : String = "F-8122-01";
        attribute chineseName : String = "控制车辆控制单元运行";
        attribute englishName : String = "Control Product 8122 operation";
        attribute functionLevel : Integer = 4;
        attribute category : String = "CONTROL";
        attribute allocatedProductCode : String = "8122";
        out item used_ITM_CMD_024 : I_ITM_CMD_024;
        out item used_ITM_CMD_009 : I_ITM_CMD_009;
        out item used_ITM_CMD_027 : I_ITM_CMD_027;
        in item used_ITM_CMD_001 : I_ITM_CMD_001;
        in item used_ITM_CMD_004 : I_ITM_CMD_004;
        out item used_ITM_CMD_029 : I_ITM_CMD_029;
        in item used_ITM_MEA_013 : I_ITM_MEA_013;
        out item used_ITM_CMD_025 : I_ITM_CMD_025;
        in item used_ITM_MEA_029 : I_ITM_MEA_029;
        in item used_ITM_CMD_030 : I_ITM_CMD_030;
        in item used_ITM_MEA_008 : I_ITM_MEA_008;
        in item used_ITM_CMD_003 : I_ITM_CMD_003;
        out item used_ITM_CMD_028 : I_ITM_CMD_028;
        in item used_ITM_MEA_001 : I_ITM_MEA_001;
        in item used_ITM_CMD_002 : I_ITM_CMD_002;
        in item used_ITM_MEA_028 : I_ITM_MEA_028;
        out item used_ITM_CMD_008 : I_ITM_CMD_008;
        out item used_ITM_CMD_026 : I_ITM_CMD_026;
    }
    action def FN_F_8122_02 {
        attribute functionId : String = "F-8122-02";
        attribute chineseName : String = "协调车辆控制单元接口交互";
        attribute englishName : String = "Coordinate Product 8122 interface interactions";
        attribute functionLevel : Integer = 4;
        attribute category : String = "COORDINATION";
        attribute allocatedProductCode : String = "8122";
        in item used_ITM_MEA_008 : I_ITM_MEA_008;
    }
    action def FN_F_8122_03 {
        attribute functionId : String = "F-8122-03";
        attribute chineseName : String = "限制并保护车辆控制单元运行";
        attribute englishName : String = "Limit and protect Product 8122 operation";
        attribute functionLevel : Integer = 4;
        attribute category : String = "PROTECTION";
        attribute allocatedProductCode : String = "8122";
        in item used_ITM_LIM_004 : I_ITM_LIM_004;
        in item used_ITM_LIM_010 : I_ITM_LIM_010;
        in item used_ITM_LIM_005 : I_ITM_LIM_005;
        in item used_ITM_LIM_009 : I_ITM_LIM_009;
        in item used_ITM_LIM_001 : I_ITM_LIM_001;
    }
    action def FN_F_8122_04 {
        attribute functionId : String = "F-8122-04";
        attribute chineseName : String = "报告车辆控制单元运行状态";
        attribute englishName : String = "Report Product 8122 operating state";
        attribute functionLevel : Integer = 4;
        attribute category : String = "STATUS_REPORTING";
        attribute allocatedProductCode : String = "8122";
        in item used_ITM_STA_019 : I_ITM_STA_019;
        in item used_ITM_STA_031 : I_ITM_STA_031;
        in item used_ITM_STA_030 : I_ITM_STA_030;
        in item used_ITM_STA_002 : I_ITM_STA_002;
        in item used_ITM_STA_001 : I_ITM_STA_001;
        in item used_ITM_STA_003 : I_ITM_STA_003;
    }
    action def FN_F_8122_05 {
        attribute functionId : String = "F-8122-05";
        attribute chineseName : String = "统计车辆控制单元运行数据";
        attribute englishName : String = "Accumulate Product 8122 operating statistics";
        attribute functionLevel : Integer = 4;
        attribute category : String = "STATISTICS";
        attribute allocatedProductCode : String = "8122";
        in item used_ITM_ACC_005 : I_ITM_ACC_005;
        in item used_ITM_ACC_002 : I_ITM_ACC_002;
        in item used_ITM_ACC_015 : I_ITM_ACC_015;
        in item used_ITM_ACC_004 : I_ITM_ACC_004;
        in item used_ITM_ACC_003 : I_ITM_ACC_003;
    }
    action def FN_F_8125_01 {
        attribute functionId : String = "F-8125-01";
        attribute chineseName : String = "控制列车级牵引控制单元运行";
        attribute englishName : String = "Control Product 8125 operation";
        attribute functionLevel : Integer = 4;
        attribute category : String = "CONTROL";
        attribute allocatedProductCode : String = "8125";
        in item used_ITM_MEA_012 : I_ITM_MEA_012;
        in item used_ITM_CMD_002 : I_ITM_CMD_002;
        in item used_ITM_MEA_008 : I_ITM_MEA_008;
        in item used_ITM_CMD_006 : I_ITM_CMD_006;
        in item used_ITM_MEA_001 : I_ITM_MEA_001;
        out item used_ITM_CMD_012 : I_ITM_CMD_012;
        out item used_ITM_MEA_013 : I_ITM_MEA_013;
        in item used_ITM_CMD_009 : I_ITM_CMD_009;
        in item used_ITM_CMD_008 : I_ITM_CMD_008;
        in item used_ITM_MEA_004 : I_ITM_MEA_004;
    }
    action def FN_F_8125_02 {
        attribute functionId : String = "F-8125-02";
        attribute chineseName : String = "协调列车级牵引控制单元接口交互";
        attribute englishName : String = "Coordinate Product 8125 interface interactions";
        attribute functionLevel : Integer = 4;
        attribute category : String = "COORDINATION";
        attribute allocatedProductCode : String = "8125";
        in item used_ITM_MEA_008 : I_ITM_MEA_008;
    }
    action def FN_F_8125_03 {
        attribute functionId : String = "F-8125-03";
        attribute chineseName : String = "限制并保护列车级牵引控制单元运行";
        attribute englishName : String = "Limit and protect Product 8125 operation";
        attribute functionLevel : Integer = 4;
        attribute category : String = "PROTECTION";
        attribute allocatedProductCode : String = "8125";
        in item used_ITM_LIM_005 : I_ITM_LIM_005;
        out item used_ITM_LIM_004 : I_ITM_LIM_004;
        out item used_ITM_LIM_003 : I_ITM_LIM_003;
        out item used_ITM_LIM_001 : I_ITM_LIM_001;
    }
    action def FN_F_8125_04 {
        attribute functionId : String = "F-8125-04";
        attribute chineseName : String = "报告列车级牵引控制单元运行状态";
        attribute englishName : String = "Report Product 8125 operating state";
        attribute functionLevel : Integer = 4;
        attribute category : String = "STATUS_REPORTING";
        attribute allocatedProductCode : String = "8125";
        in item used_ITM_STA_026 : I_ITM_STA_026;
        out item used_ITM_STA_019 : I_ITM_STA_019;
        out item used_ITM_STA_002 : I_ITM_STA_002;
        out item used_ITM_STA_001 : I_ITM_STA_001;
        out item used_ITM_STA_018 : I_ITM_STA_018;
        out item used_ITM_STA_017 : I_ITM_STA_017;
    }
    action def FN_F_8127_01 {
        attribute functionId : String = "F-8127-01";
        attribute chineseName : String = "路由ATP接口单元输入输出信号";
        attribute englishName : String = "Route input and output signals through Product 8127";
        attribute functionLevel : Integer = 4;
        attribute category : String = "CONTROL";
        attribute allocatedProductCode : String = "8127";
        out item used_ITM_CMD_030 : I_ITM_CMD_030;
    }
    action def FN_F_8127_02 {
        attribute functionId : String = "F-8127-02";
        attribute chineseName : String = "报告ATP接口单元运行状态";
        attribute englishName : String = "Report Product 8127 operating state";
        attribute functionLevel : Integer = 4;
        attribute category : String = "STATUS_REPORTING";
        attribute allocatedProductCode : String = "8127";
        out item used_ITM_STA_027 : I_ITM_STA_027;
    }
    action def FN_F_8128_01 {
        attribute functionId : String = "F-8128-01";
        attribute chineseName : String = "路由输入输出单元输入输出信号";
        attribute englishName : String = "Route input and output signals through Product 8128";
        attribute functionLevel : Integer = 4;
        attribute category : String = "CONTROL";
        attribute allocatedProductCode : String = "8128";
        out item used_ITM_MEA_016 : I_ITM_MEA_016;
        out item used_ITM_MEA_026 : I_ITM_MEA_026;
        in item used_ITM_MEA_014 : I_ITM_MEA_014;
        in item used_ITM_MEA_027 : I_ITM_MEA_027;
        out item used_ITM_CMD_024 : I_ITM_CMD_024;
        out item used_ITM_MEA_025 : I_ITM_MEA_025;
    }
    action def FN_F_8128_02 {
        attribute functionId : String = "F-8128-02";
        attribute chineseName : String = "协调输入输出单元接口交互";
        attribute englishName : String = "Coordinate Product 8128 interface interactions";
        attribute functionLevel : Integer = 4;
        attribute category : String = "COORDINATION";
        attribute allocatedProductCode : String = "8128";
        in item used_ITM_STA_027 : I_ITM_STA_027;
    }
    action def FN_F_8128_03 {
        attribute functionId : String = "F-8128-03";
        attribute chineseName : String = "报告输入输出单元运行状态";
        attribute englishName : String = "Report Product 8128 operating state";
        attribute functionLevel : Integer = 4;
        attribute category : String = "STATUS_REPORTING";
        attribute allocatedProductCode : String = "8128";
        in item used_ITM_STA_024 : I_ITM_STA_024;
        in item used_ITM_STA_027 : I_ITM_STA_027;
        in item used_ITM_STA_025 : I_ITM_STA_025;
        in item used_ITM_STA_026 : I_ITM_STA_026;
    }
    action def FN_F_8150_01 {
        attribute functionId : String = "F-8150-01";
        attribute chineseName : String = "执行安全控制、反馈运行状态";
        attribute englishName : String = "Execute safety control; Report status";
        attribute functionLevel : Integer = 3;
        attribute category : String = "SAFETY";
        attribute allocatedProductCode : String = "8150";
    }
    action def FN_F_8151_01 {
        attribute functionId : String = "F-8151-01";
        attribute chineseName : String = "执行高压安全回路安全逻辑";
        attribute englishName : String = "Execute Product 8151 safety logic";
        attribute functionLevel : Integer = 4;
        attribute category : String = "SAFETY";
        attribute allocatedProductCode : String = "8151";
        in item used_ITM_CMD_016 : I_ITM_CMD_016;
    }
    action def FN_F_8151_02 {
        attribute functionId : String = "F-8151-02";
        attribute chineseName : String = "报告高压安全回路运行状态";
        attribute englishName : String = "Report Product 8151 operating state";
        attribute functionLevel : Integer = 4;
        attribute category : String = "STATUS_REPORTING";
        attribute allocatedProductCode : String = "8151";
        out item used_ITM_STA_024 : I_ITM_STA_024;
    }
    action def FN_F_8152_01 {
        attribute functionId : String = "F-8152-01";
        attribute chineseName : String = "执行制动安全回路安全逻辑";
        attribute englishName : String = "Execute Product 8152 safety logic";
        attribute functionLevel : Integer = 4;
        attribute category : String = "SAFETY";
        attribute allocatedProductCode : String = "8152";
        in item used_ITM_CMD_004 : I_ITM_CMD_004;
        in item used_ITM_CMD_030 : I_ITM_CMD_030;
    }
    action def FN_F_8152_02 {
        attribute functionId : String = "F-8152-02";
        attribute chineseName : String = "报告制动安全回路运行状态";
        attribute englishName : String = "Report Product 8152 operating state";
        attribute functionLevel : Integer = 4;
        attribute category : String = "STATUS_REPORTING";
        attribute allocatedProductCode : String = "8152";
        out item used_ITM_STA_025 : I_ITM_STA_025;
    }
    action def FN_F_8154_01 {
        attribute functionId : String = "F-8154-01";
        attribute chineseName : String = "执行牵引安全回路安全逻辑";
        attribute englishName : String = "Execute Product 8154 safety logic";
        attribute functionLevel : Integer = 4;
        attribute category : String = "SAFETY";
        attribute allocatedProductCode : String = "8154";
        in item used_ITM_CMD_009 : I_ITM_CMD_009;
        in item used_ITM_CMD_008 : I_ITM_CMD_008;
    }
    action def FN_F_8154_02 {
        attribute functionId : String = "F-8154-02";
        attribute chineseName : String = "报告牵引安全回路运行状态";
        attribute englishName : String = "Report Product 8154 operating state";
        attribute functionLevel : Integer = 4;
        attribute category : String = "STATUS_REPORTING";
        attribute allocatedProductCode : String = "8154";
        out item used_ITM_STA_026 : I_ITM_STA_026;
    }
    action def FN_F_8160_01 {
        attribute functionId : String = "F-8160-01";
        attribute chineseName : String = "控制运行、反馈运行状态";
        attribute englishName : String = "Control operation; Report status";
        attribute functionLevel : Integer = 3;
        attribute category : String = "COORDINATION";
        attribute allocatedProductCode : String = "8160";
    }
    action def FN_F_8166_01 {
        attribute functionId : String = "F-8166-01";
        attribute chineseName : String = "控制能量计运行";
        attribute englishName : String = "Control Product 8166 operation";
        attribute functionLevel : Integer = 4;
        attribute category : String = "CONTROL";
        attribute allocatedProductCode : String = "8166";
        in item used_ITM_MEA_006 : I_ITM_MEA_006;
        in item used_ITM_MEA_009 : I_ITM_MEA_009;
        in item used_ITM_MEA_005 : I_ITM_MEA_005;
        in item used_ITM_MEA_008 : I_ITM_MEA_008;
    }
    action def FN_F_8166_02 {
        attribute functionId : String = "F-8166-02";
        attribute chineseName : String = "协调能量计接口交互";
        attribute englishName : String = "Coordinate Product 8166 interface interactions";
        attribute functionLevel : Integer = 4;
        attribute category : String = "COORDINATION";
        attribute allocatedProductCode : String = "8166";
        in item used_ITM_MEA_008 : I_ITM_MEA_008;
    }
    action def FN_F_8166_03 {
        attribute functionId : String = "F-8166-03";
        attribute chineseName : String = "报告能量计运行状态";
        attribute englishName : String = "Report Product 8166 operating state";
        attribute functionLevel : Integer = 4;
        attribute category : String = "STATUS_REPORTING";
        attribute allocatedProductCode : String = "8166";
        out item used_ITM_STA_035 : I_ITM_STA_035;
    }
    action def FN_F_8166_04 {
        attribute functionId : String = "F-8166-04";
        attribute chineseName : String = "统计能量计运行数据";
        attribute englishName : String = "Accumulate Product 8166 operating statistics";
        attribute functionLevel : Integer = 4;
        attribute category : String = "STATISTICS";
        attribute allocatedProductCode : String = "8166";
        out item used_ITM_ACC_012 : I_ITM_ACC_012;
        out item used_ITM_ACC_014 : I_ITM_ACC_014;
        out item used_ITM_ACC_005 : I_ITM_ACC_005;
        out item used_ITM_ACC_001 : I_ITM_ACC_001;
        out item used_ITM_ACC_011 : I_ITM_ACC_011;
        out item used_ITM_ACC_007 : I_ITM_ACC_007;
        out item used_ITM_ACC_015 : I_ITM_ACC_015;
        out item used_ITM_ACC_010 : I_ITM_ACC_010;
        out item used_ITM_ACC_009 : I_ITM_ACC_009;
        out item used_ITM_ACC_003 : I_ITM_ACC_003;
        out item used_ITM_ACC_008 : I_ITM_ACC_008;
        out item used_ITM_ACC_004 : I_ITM_ACC_004;
        out item used_ITM_ACC_002 : I_ITM_ACC_002;
    }
    action def FN_F_D000_01 {
        attribute functionId : String = "F-D000-01";
        attribute chineseName : String = "控制运行";
        attribute englishName : String = "Control operation";
        attribute functionLevel : Integer = 1;
        attribute category : String = "COORDINATION";
        attribute allocatedProductCode : String = "D000";
    }
    action def FN_F_D100_01 {
        attribute functionId : String = "F-D100-01";
        attribute chineseName : String = "控制运行";
        attribute englishName : String = "Control operation";
        attribute functionLevel : Integer = 2;
        attribute category : String = "COORDINATION";
        attribute allocatedProductCode : String = "D100";
    }
    action def FN_F_D110_01 {
        attribute functionId : String = "F-D110-01";
        attribute chineseName : String = "控制运行";
        attribute englishName : String = "Control operation";
        attribute functionLevel : Integer = 3;
        attribute category : String = "COORDINATION";
        attribute allocatedProductCode : String = "D110";
    }
    action def FN_F_D112_01 {
        attribute functionId : String = "F-D112-01";
        attribute chineseName : String = "提供方向操作元件边界交互";
        attribute englishName : String = "Provide boundary interaction for Product D112";
        attribute functionLevel : Integer = 4;
        attribute category : String = "CONTROL";
        attribute allocatedProductCode : String = "D112";
        out item used_ITM_CMD_001 : I_ITM_CMD_001;
    }
    action def FN_F_D113_01 {
        attribute functionId : String = "F-D113-01";
        attribute chineseName : String = "提供牵引操作元件边界交互";
        attribute englishName : String = "Provide boundary interaction for Product D113";
        attribute functionLevel : Integer = 4;
        attribute category : String = "CONTROL";
        attribute allocatedProductCode : String = "D113";
        out item used_ITM_CMD_002 : I_ITM_CMD_002;
    }
    action def FN_F_D114_01 {
        attribute functionId : String = "F-D114-01";
        attribute chineseName : String = "提供制动操作元件边界交互";
        attribute englishName : String = "Provide boundary interaction for Product D114";
        attribute functionLevel : Integer = 4;
        attribute category : String = "CONTROL";
        attribute allocatedProductCode : String = "D114";
        out item used_ITM_CMD_003 : I_ITM_CMD_003;
    }
    action def FN_F_D120_01 {
        attribute functionId : String = "F-D120-01";
        attribute chineseName : String = "控制运行";
        attribute englishName : String = "Control operation";
        attribute functionLevel : Integer = 3;
        attribute category : String = "COORDINATION";
        attribute allocatedProductCode : String = "D120";
    }
    action def FN_F_D121_01 {
        attribute functionId : String = "F-D121-01";
        attribute chineseName : String = "提供紧急制动按钮边界交互";
        attribute englishName : String = "Provide boundary interaction for Product D121";
        attribute functionLevel : Integer = 4;
        attribute category : String = "CONTROL";
        attribute allocatedProductCode : String = "D121";
        out item used_ITM_CMD_004 : I_ITM_CMD_004;
    }
    action def FN_F_D130_01 {
        attribute functionId : String = "F-D130-01";
        attribute chineseName : String = "控制运行";
        attribute englishName : String = "Control operation";
        attribute functionLevel : Integer = 3;
        attribute category : String = "COORDINATION";
        attribute allocatedProductCode : String = "D130";
    }
    action def FN_F_D13B_01 {
        attribute functionId : String = "F-D13B-01";
        attribute chineseName : String = "提供撒砂按钮边界交互";
        attribute englishName : String = "Provide boundary interaction for Product D13B";
        attribute functionLevel : Integer = 4;
        attribute category : String = "CONTROL";
        attribute allocatedProductCode : String = "D13B";
        out item used_ITM_CMD_024 : I_ITM_CMD_024;
    }
    action def FN_F_E000_01 {
        attribute functionId : String = "F-E000-01";
        attribute chineseName : String = "控制运行";
        attribute englishName : String = "Control operation";
        attribute functionLevel : Integer = 1;
        attribute category : String = "COORDINATION";
        attribute allocatedProductCode : String = "E000";
    }
    action def FN_F_E100_01 {
        attribute functionId : String = "F-E100-01";
        attribute chineseName : String = "提供ATP车载边界交互";
        attribute englishName : String = "Provide boundary interaction for Product E100";
        attribute functionLevel : Integer = 2;
        attribute category : String = "CONTROL";
        attribute allocatedProductCode : String = "E100";
        out item used_ITM_CMD_030 : I_ITM_CMD_030;
        out item used_ITM_STA_027 : I_ITM_STA_027;
    }
    action def FN_F_X000_01 {
        attribute functionId : String = "F-X000-01";
        attribute chineseName : String = "实现车载再生能量回收与利用";
        attribute englishName : String = "Provide onboard regenerative-energy recovery and reuse";
        attribute functionLevel : Integer = 1;
        attribute category : String = "COORDINATION";
        attribute allocatedProductCode : String = "X000";
    }
    action def FN_F_X100_01 {
        attribute functionId : String = "F-X100-01";
        attribute chineseName : String = "吸收、存储并按需释放再生制动能量";
        attribute englishName : String = "Absorb, store and release regenerative braking energy on demand";
        attribute functionLevel : Integer = 2;
        attribute category : String = "COORDINATION";
        attribute allocatedProductCode : String = "X100";
    }
    action def FN_F_X110_01 {
        attribute functionId : String = "F-X110-01";
        attribute chineseName : String = "实现再生储能双向能量变换、控制与保护";
        attribute englishName : String = "Provide bidirectional regenerative-storage conversion, control and protection";
        attribute functionLevel : Integer = 3;
        attribute category : String = "COORDINATION";
        attribute allocatedProductCode : String = "X110";
    }
    action def FN_F_X111_01 {
        attribute functionId : String = "F-X111-01";
        attribute chineseName : String = "实现中间直流母线与储能侧直流母线双向能量转换";
        attribute englishName : String = "Convert energy bidirectionally between DC link and storage DC bus";
        attribute functionLevel : Integer = 4;
        attribute category : String = "PHYSICAL_TRANSFORMATION";
        attribute allocatedProductCode : String = "X111";
        inout item used_ITM_PHY_003 : I_ITM_PHY_003;
        inout item used_ITM_PHY_016 : I_ITM_PHY_016;
    }
    action def FN_F_X111_02 {
        attribute functionId : String = "F-X111-02";
        attribute chineseName : String = "执行双向DC/DC功率变换指令并反馈状态";
        attribute englishName : String = "Execute bidirectional DC/DC power commands and report state";
        attribute functionLevel : Integer = 4;
        attribute category : String = "CONTROL";
        attribute allocatedProductCode : String = "X111";
        out item used_ITM_STA_029 : I_ITM_STA_029;
        in item used_ITM_CMD_026 : I_ITM_CMD_026;
        in item used_ITM_CMD_025 : I_ITM_CMD_025;
        out item used_ITM_STA_028 : I_ITM_STA_028;
        out item used_ITM_MEA_030 : I_ITM_MEA_030;
        out item used_ITM_MEA_029 : I_ITM_MEA_029;
    }
    action def FN_F_X112_01 {
        attribute functionId : String = "F-X112-01";
        attribute chineseName : String = "控制双向DC/DC功率变换";
        attribute englishName : String = "Control bidirectional DC/DC power conversion";
        attribute functionLevel : Integer = 4;
        attribute category : String = "CONTROL";
        attribute allocatedProductCode : String = "X112";
        in item used_ITM_CMD_026 : I_ITM_CMD_026;
        out item used_ITM_CMD_028 : I_ITM_CMD_028;
        in item used_ITM_MEA_025 : I_ITM_MEA_025;
        in item used_ITM_MEA_026 : I_ITM_MEA_026;
        in item used_ITM_CMD_029 : I_ITM_CMD_029;
        in item used_ITM_MEA_029 : I_ITM_MEA_029;
        in item used_ITM_CMD_025 : I_ITM_CMD_025;
        out item used_ITM_CMD_027 : I_ITM_CMD_027;
        in item used_ITM_MEA_008 : I_ITM_MEA_008;
        in item used_ITM_MEA_030 : I_ITM_MEA_030;
        in item used_ITM_MEA_028 : I_ITM_MEA_028;
        in item used_ITM_MEA_027 : I_ITM_MEA_027;
    }
    action def FN_F_X112_02 {
        attribute functionId : String = "F-X112-02";
        attribute chineseName : String = "限制储能充放电功率并协调保护";
        attribute englishName : String = "Limit storage charge-discharge power and coordinate protection";
        attribute functionLevel : Integer = 4;
        attribute category : String = "PROTECTION";
        attribute allocatedProductCode : String = "X112";
        out item used_ITM_LIM_011 : I_ITM_LIM_011;
        out item used_ITM_LIM_012 : I_ITM_LIM_012;
        out item used_ITM_LIM_010 : I_ITM_LIM_010;
        in item used_ITM_LIM_007 : I_ITM_LIM_007;
        out item used_ITM_LIM_009 : I_ITM_LIM_009;
    }
    action def FN_F_X112_03 {
        attribute functionId : String = "F-X112-03";
        attribute chineseName : String = "报告储能变换系统状态";
        attribute englishName : String = "Report energy-storage conversion system state";
        attribute functionLevel : Integer = 4;
        attribute category : String = "STATUS_REPORTING";
        attribute allocatedProductCode : String = "X112";
        out item used_ITM_STA_030 : I_ITM_STA_030;
        out item used_ITM_STA_028 : I_ITM_STA_028;
        in item used_ITM_STA_033 : I_ITM_STA_033;
        out item used_ITM_ACC_004 : I_ITM_ACC_004;
        in item used_ITM_STA_034 : I_ITM_STA_034;
        in item used_ITM_STA_032 : I_ITM_STA_032;
        out item used_ITM_STA_031 : I_ITM_STA_031;
        out item used_ITM_STA_029 : I_ITM_STA_029;
    }
    action def FN_F_X113_01 {
        attribute functionId : String = "F-X113-01";
        attribute chineseName : String = "检测双向DC/DC检测保护组件状态";
        attribute englishName : String = "Measure state at Product X113";
        attribute functionLevel : Integer = 4;
        attribute category : String = "MEASUREMENT";
        attribute allocatedProductCode : String = "X113";
        out item used_ITM_MEA_027 : I_ITM_MEA_027;
        out item used_ITM_MEA_025 : I_ITM_MEA_025;
        out item used_ITM_STA_031 : I_ITM_STA_031;
        out item used_ITM_LIM_010 : I_ITM_LIM_010;
        out item used_ITM_MEA_026 : I_ITM_MEA_026;
        out item used_ITM_MEA_008 : I_ITM_MEA_008;
        inout item used_ITM_PHY_016 : I_ITM_PHY_016;
        out item used_ITM_STA_034 : I_ITM_STA_034;
        out item used_ITM_LIM_007 : I_ITM_LIM_007;
        inout item used_ITM_PHY_003 : I_ITM_PHY_003;
        out item used_ITM_MEA_030 : I_ITM_MEA_030;
        out item used_ITM_LIM_009 : I_ITM_LIM_009;
        inout item used_ITM_PHY_015 : I_ITM_PHY_015;
        out item used_ITM_STA_029 : I_ITM_STA_029;
    }
    action def FN_F_X120_01 {
        attribute functionId : String = "F-X120-01";
        attribute chineseName : String = "储存与释放能量、检测运行参数";
        attribute englishName : String = "Store and release energy; Measure parameters";
        attribute functionLevel : Integer = 3;
        attribute category : String = "PHYSICAL_TRANSFORMATION";
        attribute allocatedProductCode : String = "X120";
    }
    action def FN_F_X121_01 {
        attribute functionId : String = "F-X121-01";
        attribute chineseName : String = "储存并按需释放再生制动电能";
        attribute englishName : String = "Store and release regenerative braking energy on demand";
        attribute functionLevel : Integer = 4;
        attribute category : String = "ENERGY_STORAGE";
        attribute allocatedProductCode : String = "X121";
        inout item used_ITM_PHY_016 : I_ITM_PHY_016;
        inout item used_ITM_PHY_013 : I_ITM_PHY_013;
    }
    action def FN_F_X121_02 {
        attribute functionId : String = "F-X121-02";
        attribute chineseName : String = "提供超级电容荷电状态反馈";
        attribute englishName : String = "Provide supercapacitor state-of-charge feedback";
        attribute functionLevel : Integer = 4;
        attribute category : String = "MEASUREMENT";
        attribute allocatedProductCode : String = "X121";
        out item used_ITM_MEA_028 : I_ITM_MEA_028;
    }
    action def FN_F_X122_01 {
        attribute functionId : String = "F-X122-01";
        attribute chineseName : String = "检测超级电容电压传感器状态";
        attribute englishName : String = "Measure state at Product X122";
        attribute functionLevel : Integer = 4;
        attribute category : String = "MEASUREMENT";
        attribute allocatedProductCode : String = "X122";
        out item used_ITM_MEA_025 : I_ITM_MEA_025;
        inout item used_ITM_PHY_016 : I_ITM_PHY_016;
    }
    action def FN_F_X123_01 {
        attribute functionId : String = "F-X123-01";
        attribute chineseName : String = "检测超级电容电流传感器状态";
        attribute englishName : String = "Measure state at Product X123";
        attribute functionLevel : Integer = 4;
        attribute category : String = "MEASUREMENT";
        attribute allocatedProductCode : String = "X123";
        out item used_ITM_MEA_026 : I_ITM_MEA_026;
        inout item used_ITM_PHY_016 : I_ITM_PHY_016;
    }
    action def FN_F_X124_01 {
        attribute functionId : String = "F-X124-01";
        attribute chineseName : String = "检测超级电容温度传感器状态";
        attribute englishName : String = "Measure state at Product X124";
        attribute functionLevel : Integer = 4;
        attribute category : String = "MEASUREMENT";
        attribute allocatedProductCode : String = "X124";
        inout item used_ITM_PHY_013 : I_ITM_PHY_013;
        out item used_ITM_MEA_027 : I_ITM_MEA_027;
    }
    action def FN_F_X130_01 {
        attribute functionId : String = "F-X130-01";
        attribute chineseName : String = "传递能量/介质";
        attribute englishName : String = "Transport energy/media";
        attribute functionLevel : Integer = 3;
        attribute category : String = "PHYSICAL_TRANSPORT";
        attribute allocatedProductCode : String = "X130";
    }
    action def FN_F_X131_01 {
        attribute functionId : String = "F-X131-01";
        attribute chineseName : String = "传递储能主接触器电能";
        attribute englishName : String = "Transmit electrical energy through Product X131";
        attribute functionLevel : Integer = 4;
        attribute category : String = "PHYSICAL_TRANSPORT";
        attribute allocatedProductCode : String = "X131";
        inout item used_ITM_PHY_016 : I_ITM_PHY_016;
    }
    action def FN_F_X132_01 {
        attribute functionId : String = "F-X132-01";
        attribute chineseName : String = "传递储能预充电组件电能";
        attribute englishName : String = "Transmit electrical energy through Product X132";
        attribute functionLevel : Integer = 4;
        attribute category : String = "PHYSICAL_TRANSPORT";
        attribute allocatedProductCode : String = "X132";
        inout item used_ITM_PHY_016 : I_ITM_PHY_016;
    }
    action def FN_F_X133_01 {
        attribute functionId : String = "F-X133-01";
        attribute chineseName : String = "传递储能支路保护组件电能";
        attribute englishName : String = "Transmit electrical energy through Product X133";
        attribute functionLevel : Integer = 4;
        attribute category : String = "PHYSICAL_TRANSPORT";
        attribute allocatedProductCode : String = "X133";
        inout item used_ITM_PHY_016 : I_ITM_PHY_016;
        inout item used_ITM_PHY_015 : I_ITM_PHY_015;
    }
}

package SystemDefinition {
    private import ScalarValues::*;
    private import InterfaceDefinitions::*;
    private import ProductDefinitions::*;
    part railSystem : RailSystemContext {
        interface c_CG_002543DBE0F9A7FBC2A3FDD3 : IF_IF_MEA_005 connect p_N_4000.p_N_4200.p_N_4230.p_N_4235.rp_6fea4b377f978aac to p_N_5000.p_N_5100.p_N_5110.p_N_5111.rp_5f90d6dd8fba4321 {
            attribute connectionId : String = "CG-002543DBE0F9A7FBC2A3FDD3";
            attribute connectionType : String = "SIGNAL";
            attribute originalPath : String = "4235::PORT::4235::高压线路电压输出::ITM-MEA-005::输出 -> 5111::PORT::5111::高压线路电压输入::ITM-MEA-005::输入";
        }
        interface c_CG_071B7693DAFA8B87ADA0A61E : IF_IF_CMD_004 connect p_N_8000.p_N_8100.p_N_8120.p_N_8121.rp_a9c7eff84933cd80 to p_N_7000.p_N_7200.p_N_7210.p_N_7211.rp_faa6c7c9931b0a58 {
            attribute connectionId : String = "CG-071B7693DAFA8B87ADA0A61E";
            attribute connectionType : String = "SIGNAL";
            attribute originalPath : String = "8121::PORT::8121::紧急制动请求输出::ITM-CMD-004::输出 -> 7211::PORT::7211::紧急制动请求输入::ITM-CMD-004::输入";
        }
        interface c_CG_07AF42BFA3927EF22F7BDDE7 : IF_IF_PHY_005 connect p_N_3000.p_N_3600.p_N_3640.p_N_3644.rp_af1c1b2c65382775 to p_N_5000.p_N_5300.p_N_5310.p_N_5311.rp_97eb613c06ae1b2e {
            attribute connectionId : String = "CG-07AF42BFA3927EF22F7BDDE7";
            attribute connectionType : String = "TAP";
            attribute originalPath : String = "3644::PORT::3644::旋转机械能端口::ITM-PHY-005::双向物理 -> 5311::PORT::5311::旋转机械能端口::ITM-PHY-005::双向物理";
        }
        interface c_CG_08375F15DCE75E45D4C45CE8 : IF_IF_LIM_005 connect p_N_5000.p_N_5100.p_N_5110.p_N_5111.rp_cd7720cf9a4eae22 to p_N_8000.p_N_8100.p_N_8120.p_N_8125.rp_1809c94f1581c7f8 {
            attribute connectionId : String = "CG-08375F15DCE75E45D4C45CE8";
            attribute connectionType : String = "SIGNAL";
            attribute originalPath : String = "5111::PORT::5111::接触网可接收功率输出::ITM-LIM-005::输出 -> 8125::PORT::8125::接触网可接收功率输入::ITM-LIM-005::输入";
        }
        interface c_CG_093EFCE58F3AB220CFEC48AC : IF_IF_ACC_004 connect p_X000.p_X100.p_X110.p_X112.rp_a59821acb0d73604 to p_N_8000.p_N_8100.p_N_8120.p_N_8122.rp_a095b9b42ab5cc7d {
            attribute connectionId : String = "CG-093EFCE58F3AB220CFEC48AC";
            attribute connectionType : String = "SIGNAL";
            attribute originalPath : String = "X112::PORT::X112::储能吸收功率输出::ITM-ACC-004::输出 -> 8122::PORT::8122::储能吸收功率输入::ITM-ACC-004::输入";
        }
        interface c_CG_0B7698B3C627150EF560B4B0 : IF_IF_STA_014 connect p_N_4000.p_N_4200.p_N_4210.p_N_4212.rp_62a902ccb2d5edf3 to p_N_4000.p_N_4200.p_N_4230.p_N_4238.rp_b46091b51fbac2ba {
            attribute connectionId : String = "CG-0B7698B3C627150EF560B4B0";
            attribute connectionType : String = "SIGNAL";
            attribute originalPath : String = "4212::PORT::4212::高压隔离开关状态输出::ITM-STA-014::输出 -> 4238::PORT::4238::高压隔离开关状态输入::ITM-STA-014::输入";
        }
        interface c_CG_0D68248E62957CCB92C5A2A5 : IF_IF_STA_027 connect p_E000.p_E100.rp_0307dc18d9537f9d to p_N_8000.p_N_8100.p_N_8120.p_N_8127.rp_a916a9847aeadebb {
            attribute connectionId : String = "CG-0D68248E62957CCB92C5A2A5";
            attribute connectionType : String = "SIGNAL";
            attribute originalPath : String = "E100::PORT::E100::ATP_外部安全系统状态输出::ITM-STA-027::输出 -> 8127::PORT::8127::ATP_外部安全系统状态输入::ITM-STA-027::输入";
        }
        interface c_CG_1102EBD35D52A38B96D5D2E7 : IF_IF_STA_003 connect p_N_7000.p_N_7200.p_N_7210.p_N_7211.rp_c021f63639408eff to p_N_8000.p_N_8100.p_N_8120.p_N_8122.rp_b1fb8856841fb7cf {
            attribute connectionId : String = "CG-1102EBD35D52A38B96D5D2E7";
            attribute connectionType : String = "SIGNAL";
            attribute originalPath : String = "7211::PORT::7211::制动系统可用状态输出::ITM-STA-003::输出 -> 8122::PORT::8122::制动系统可用状态输入::ITM-STA-003::输入";
        }
        interface c_CG_117A3F0E6C8FF8FF0013A46B : IF_IF_PHY_014 connect p_N_4000.p_N_4500.p_N_4510.p_N_4513.rp_f597e9dc63931270 to p_N_5000.p_N_5100.p_N_5120.p_N_5122.rp_0b57347688ba1240 {
            attribute connectionId : String = "CG-117A3F0E6C8FF8FF0013A46B";
            attribute connectionType : String = "SERIES";
            attribute originalPath : String = "4513::PORT::4513::第二交流电能端口::ITM-PHY-014::双向物理 -> 5122::PORT::5122::牵引变压器次级交流电能端口::ITM-PHY-014::双向物理";
        }
        interface c_CG_118F2C2B84D1D301C7BE63F8 : IF_IF_PHY_014 connect p_N_4000.p_N_4500.p_N_4510.p_N_4513.rp_f597e9dc63931270 to p_N_5000.p_N_5100.p_N_5120.p_N_5121.rp_9dedfe88c8a34261 {
            attribute connectionId : String = "CG-118F2C2B84D1D301C7BE63F8";
            attribute connectionType : String = "SERIES";
            attribute originalPath : String = "4513::PORT::4513::第二交流电能端口::ITM-PHY-014::双向物理 -> 5121::PORT::5121::牵引变压器次级交流电能端口::ITM-PHY-014::双向物理";
        }
        interface c_CG_121266057FF9E69E8769A5CA : IF_IF_CMD_002 connect p_N_8000.p_N_8100.p_N_8120.p_N_8121.rp_809f8275c004ab18 to p_N_8000.p_N_8100.p_N_8120.p_N_8122.rp_c39f0a202834bb12 {
            attribute connectionId : String = "CG-121266057FF9E69E8769A5CA";
            attribute connectionType : String = "SIGNAL";
            attribute originalPath : String = "8121::PORT::8121::牵引指令输出::ITM-CMD-002::输出 -> 8122::PORT::8122::牵引指令输入::ITM-CMD-002::输入";
        }
        interface c_CG_13AAF69570338FD5B6C27BC3 : IF_IF_PHY_014 connect p_N_5000.p_N_5100.p_N_5120.p_N_5122.rp_0b57347688ba1240 to p_N_5000.p_N_5100.p_N_5130.p_N_5131.rp_32d77ca0c1d88b50 {
            attribute connectionId : String = "CG-13AAF69570338FD5B6C27BC3";
            attribute connectionType : String = "SERIES";
            attribute originalPath : String = "5122::PORT::5122::牵引变压器次级交流电能端口::ITM-PHY-014::双向物理 -> 5131::PORT::5131::牵引变压器次级交流电能端口::ITM-PHY-014::双向物理";
        }
        interface c_CG_14318213721CBD91F198F77B : IF_IF_CMD_008 connect p_N_8000.p_N_8100.p_N_8120.p_N_8121.rp_c49f12594ff56025 to p_N_8000.p_N_8100.p_N_8120.p_N_8125.rp_d86bd7909c634e71 {
            attribute connectionId : String = "CG-14318213721CBD91F198F77B";
            attribute connectionType : String = "SIGNAL";
            attribute originalPath : String = "8121::PORT::8121::牵引切除请求输出::ITM-CMD-008::输出 -> 8125::PORT::8125::牵引切除请求输入::ITM-CMD-008::输入";
        }
        interface c_CG_14D79A46EA4824EAC69F2DCF : IF_IF_STA_002 connect p_N_8000.p_N_8100.p_N_8120.p_N_8125.rp_dae11d7502a6c37a to p_N_8000.p_N_8100.p_N_8120.p_N_8122.rp_ca63e6a6492a217f {
            attribute connectionId : String = "CG-14D79A46EA4824EAC69F2DCF";
            attribute connectionType : String = "SIGNAL";
            attribute originalPath : String = "8125::PORT::8125::动态制动可用状态输出::ITM-STA-002::输出 -> 8122::PORT::8122::动态制动可用状态输入::ITM-STA-002::输入";
        }
        interface c_CG_166B9301CD54035D82DA7711 : IF_IF_STA_034 connect p_X000.p_X100.p_X130.p_X133.rp_ffcdb33099ab8a28 to p_X000.p_X100.p_X110.p_X112.rp_00da2edc928b715d {
            attribute connectionId : String = "CG-166B9301CD54035D82DA7711";
            attribute connectionType : String = "SIGNAL";
            attribute originalPath : String = "X133::PORT::X133::储能保护跳闸状态输出::ITM-STA-034::输出 -> X112::PORT::X112::储能保护跳闸状态输入::ITM-STA-034::输入";
        }
        interface c_CG_1687BE836F7FC44BCDADF2D2 : IF_IF_MEA_022 connect p_N_4000.p_N_4500.p_N_4510.p_N_4517.rp_b094956bc66dfaad to p_N_4000.p_N_4500.p_N_4510.p_N_4518.rp_f46b3d97e0fceb9e {
            attribute connectionId : String = "CG-1687BE836F7FC44BCDADF2D2";
            attribute connectionType : String = "SIGNAL";
            attribute originalPath : String = "4517::PORT::4517::主变压器温度输出::ITM-MEA-022::输出 -> 4518::PORT::4518::主变压器温度输入::ITM-MEA-022::输入";
        }
        interface c_CG_169E84593A2DDD6DA3BAE4D5 : IF_IF_MEA_028 connect p_X000.p_X100.p_X120.p_X121.rp_b6cf5a49ced52abf to p_X000.p_X100.p_X110.p_X112.rp_ced58e17348ff578 {
            attribute connectionId : String = "CG-169E84593A2DDD6DA3BAE4D5";
            attribute connectionType : String = "SIGNAL";
            attribute originalPath : String = "X121::PORT::X121::超级电容SOC输出::ITM-MEA-028::输出 -> X112::PORT::X112::超级电容SOC输入::ITM-MEA-028::输入";
        }
        interface c_CG_1803BC1FF5BB8C1A4F69CBA8 : IF_IF_PHY_014 connect p_N_4000.p_N_4500.p_N_4510.p_N_4511.rp_a6f93ee77144741e to p_N_4000.p_N_4500.p_N_4510.p_N_4513.rp_88e2bd038f100aa3 {
            attribute connectionId : String = "CG-1803BC1FF5BB8C1A4F69CBA8";
            attribute connectionType : String = "SERIES";
            attribute originalPath : String = "4511::PORT::4511::牵引变压器次级交流电能端口::ITM-PHY-014::双向物理 -> 4513::PORT::4513::第一交流电能端口::ITM-PHY-014::双向物理";
        }
        interface c_CG_1A5B4FFFE2C9C8ED85759C3D : IF_IF_STA_005 connect p_N_7000.p_N_7200.p_N_7210.p_N_7211.rp_ef5148faa6dc1c65 to p_N_7000.p_N_7200.p_N_7280.p_N_7281.rp_28b3abdb6d1d1e9e {
            attribute connectionId : String = "CG-1A5B4FFFE2C9C8ED85759C3D";
            attribute connectionType : String = "SIGNAL";
            attribute originalPath : String = "7211::PORT::7211::制动缓解状态输出::ITM-STA-005::输出 -> 7281::PORT::7281::制动缓解状态输入::ITM-STA-005::输入";
        }
        interface c_CG_1ACF37CC65D3FF235E8BD75C : IF_IF_STA_002 connect p_N_8000.p_N_8100.p_N_8120.p_N_8125.rp_dae11d7502a6c37a to p_N_7000.p_N_7200.p_N_7210.p_N_7211.rp_d26568a796272d7a {
            attribute connectionId : String = "CG-1ACF37CC65D3FF235E8BD75C";
            attribute connectionType : String = "SIGNAL";
            attribute originalPath : String = "8125::PORT::8125::动态制动可用状态输出::ITM-STA-002::输出 -> 7211::PORT::7211::动态制动可用状态输入::ITM-STA-002::输入";
        }
        interface c_CG_1AE13610E33C0DC7055CFCED : IF_IF_CMD_027 connect p_N_8000.p_N_8100.p_N_8120.p_N_8122.rp_4683a7cb63e55daf to p_X000.p_X100.p_X110.p_X112.rp_81f1c1da5d6d3173 {
            attribute connectionId : String = "CG-1AE13610E33C0DC7055CFCED";
            attribute connectionType : String = "SIGNAL";
            attribute originalPath : String = "8122::PORT::8122::储能主接触器指令输出::ITM-CMD-027::输出 -> X112::PORT::X112::储能主接触器指令输入::ITM-CMD-027::输入";
        }
        interface c_CG_1AEA8B915E14A5D0FFEE30D9 : IF_IF_MEA_016 connect p_N_8000.p_N_8100.p_N_8120.p_N_8128.rp_0e19632016b69ff2 to p_N_7000.p_N_7200.p_N_7210.p_N_7211.rp_f786158194c89c8a {
            attribute connectionId : String = "CG-1AEA8B915E14A5D0FFEE30D9";
            attribute connectionType : String = "SIGNAL";
            attribute originalPath : String = "8128::PORT::8128::制动缸压力输出::ITM-MEA-016::输出 -> 7211::PORT::7211::制动缸压力输入::ITM-MEA-016::输入";
        }
        interface c_CG_1BA0ACBF380D191A9BED4AE4 : IF_IF_MEA_027 connect p_X000.p_X100.p_X120.p_X124.rp_5083db510ca305a5 to p_X000.p_X100.p_X110.p_X112.rp_848f140649f8e2ae {
            attribute connectionId : String = "CG-1BA0ACBF380D191A9BED4AE4";
            attribute connectionType : String = "SIGNAL";
            attribute originalPath : String = "X124::PORT::X124::超级电容温度输出::ITM-MEA-027::输出 -> X112::PORT::X112::超级电容温度输入::ITM-MEA-027::输入";
        }
        interface c_CG_1BF39653E0AA099A8515E223 : IF_IF_PHY_013 connect p_X000.p_X100.p_X120.p_X124.rp_4d5eafc70549d9c0 to p_X000.p_X100.p_X120.p_X121.rp_387cdae1b4483182 {
            attribute connectionId : String = "CG-1BF39653E0AA099A8515E223";
            attribute connectionType : String = "TAP";
            attribute originalPath : String = "X124::PORT::X124::超级电容热能感知端口::ITM-PHY-013::双向物理 -> X121::PORT::X121::热能_热流端口::ITM-PHY-013::双向物理";
        }
        interface c_CG_1C5FC46A1E7682144A3BDDDF : IF_IF_MEA_005 connect p_N_4000.p_N_4200.p_N_4230.p_N_4238.rp_5576b5e0dbb912ba to p_N_8000.p_N_8100.p_N_8160.p_N_8166.rp_573e029523ef9946 {
            attribute connectionId : String = "CG-1C5FC46A1E7682144A3BDDDF";
            attribute connectionType : String = "SIGNAL";
            attribute originalPath : String = "4238::PORT::4238::高压线路电压输出::ITM-MEA-005::输出 -> 8166::PORT::8166::高压线路电压输入::ITM-MEA-005::输入";
        }
        interface c_CG_1D4D143F52B7F4D880B3CB30 : IF_IF_CMD_019 connect p_N_7000.p_N_7200.p_N_7210.p_N_7211.rp_abc190a288d4c9d5 to p_N_7000.p_N_7200.p_N_7220.p_N_7227.rp_f645a5b55a3683c6 {
            attribute connectionId : String = "CG-1D4D143F52B7F4D880B3CB30";
            attribute connectionType : String = "SIGNAL";
            attribute originalPath : String = "7211::PORT::7211::制动缓解指令输出::ITM-CMD-019::输出 -> 7227::PORT::7227::制动缓解指令输入::ITM-CMD-019::输入";
        }
        interface c_CG_1D8165FC25AEFF761DD29797 : IF_IF_CMD_004 connect p_N_8000.p_N_8100.p_N_8120.p_N_8121.rp_a9c7eff84933cd80 to p_N_8000.p_N_8100.p_N_8120.p_N_8122.rp_361e7dc74e9287e3 {
            attribute connectionId : String = "CG-1D8165FC25AEFF761DD29797";
            attribute connectionType : String = "SIGNAL";
            attribute originalPath : String = "8121::PORT::8121::紧急制动请求输出::ITM-CMD-004::输出 -> 8122::PORT::8122::紧急制动请求输入::ITM-CMD-004::输入";
        }
        interface c_CG_20C0A22ECCF07864FDBA3F5A : IF_IF_MEA_006 connect p_N_4000.p_N_4200.p_N_4230.p_N_4236.rp_9107465175683792 to p_N_5000.p_N_5100.p_N_5110.p_N_5111.rp_651700e69b7dccba {
            attribute connectionId : String = "CG-20C0A22ECCF07864FDBA3F5A";
            attribute connectionType : String = "SIGNAL";
            attribute originalPath : String = "4236::PORT::4236::高压线路电流输出::ITM-MEA-006::输出 -> 5111::PORT::5111::高压线路电流输入::ITM-MEA-006::输入";
        }
        interface c_CG_2274BA128E639FDE4D4F56EC : IF_IF_STA_016 connect p_N_4000.p_N_4500.p_N_4510.p_N_4517.rp_b93b1716e8b4e844 to p_N_4000.p_N_4200.p_N_4230.p_N_4238.rp_11b7e7965ec2e386 {
            attribute connectionId : String = "CG-2274BA128E639FDE4D4F56EC";
            attribute connectionType : String = "SIGNAL";
            attribute originalPath : String = "4517::PORT::4517::高压系统故障状态输出::ITM-STA-016::输出 -> 4238::PORT::4238::高压系统故障状态输入::ITM-STA-016::输入";
        }
        interface c_CG_25DC22E45A984D1CB28D188B : IF_IF_CMD_026 connect p_N_8000.p_N_8100.p_N_8120.p_N_8122.rp_a4aac084c46e1e57 to p_X000.p_X100.p_X110.p_X112.rp_1164249ec859b807 {
            attribute connectionId : String = "CG-25DC22E45A984D1CB28D188B";
            attribute connectionType : String = "SIGNAL";
            attribute originalPath : String = "8122::PORT::8122::双向DC_DC使能输出::ITM-CMD-026::输出 -> X112::PORT::X112::双向DC_DC使能输入::ITM-CMD-026::输入";
        }
        interface c_CG_2B17DCC398F786E916C9C8DC : IF_IF_CMD_022 connect p_N_7000.p_N_7200.p_N_7210.p_N_7211.rp_c4074d88ed5949ec to p_N_7000.p_N_7200.p_N_7220.p_N_7225.rp_8e705d6c34197ff6 {
            attribute connectionId : String = "CG-2B17DCC398F786E916C9C8DC";
            attribute connectionType : String = "SIGNAL";
            attribute originalPath : String = "7211::PORT::7211::制动电磁阀指令输出::ITM-CMD-022::输出 -> 7225::PORT::7225::制动电磁阀指令输入::ITM-CMD-022::输入";
        }
        interface c_CG_2C24BA16EF5F2F7E99733CD6 : IF_IF_PHY_013 connect p_N_4000.p_N_4400.p_N_4410.p_N_4412.rp_b031f017471c85ee to boundary_BOUNDARY_THERMAL_ENVIRONMENT.bp_2ac3a221090b246a {
            attribute connectionId : String = "CG-2C24BA16EF5F2F7E99733CD6";
            attribute connectionType : String = "BOUNDARY";
            attribute originalPath : String = "4412::PORT::4412::热能_热流端口::ITM-PHY-013::双向物理 -> BOUNDARY-THERMAL-ENVIRONMENT::BPORT::BOUNDARY-THERMAL-ENVIRONMENT::ITM-PHY-013";
        }
        interface c_CG_2C4335E39D698D9A34096F73 : IF_IF_CMD_009 connect p_N_8000.p_N_8100.p_N_8120.p_N_8121.rp_f4c8eaaf49d11d3d to p_N_8000.p_N_8100.p_N_8150.p_N_8154.rp_c3d327abebd9ecfd {
            attribute connectionId : String = "CG-2C4335E39D698D9A34096F73";
            attribute connectionType : String = "SIGNAL";
            attribute originalPath : String = "8121::PORT::8121::牵引使能指令输出::ITM-CMD-009::输出 -> 8154::PORT::8154::牵引使能指令输入::ITM-CMD-009::输入";
        }
        interface c_CG_2CE5C7F366544DF5F5AB234B : IF_IF_STA_025 connect p_N_8000.p_N_8100.p_N_8150.p_N_8152.rp_ae53feffb1e116e3 to p_N_8000.p_N_8100.p_N_8120.p_N_8128.rp_eea6ab94a057e9f5 {
            attribute connectionId : String = "CG-2CE5C7F366544DF5F5AB234B";
            attribute connectionType : String = "SIGNAL";
            attribute originalPath : String = "8152::PORT::8152::制动安全回路状态输出::ITM-STA-025::输出 -> 8128::PORT::8128::制动安全回路状态输入::ITM-STA-025::输入";
        }
        interface c_CG_2E8F3CC8A8EBCDE6B7CF4D27 : IF_IF_CMD_002 connect p_D000.p_D100.p_D110.p_D113.rp_9ca0d9d396f8ffd0 to p_N_8000.p_N_8100.p_N_8120.p_N_8121.rp_a49a67fafe112278 {
            attribute connectionId : String = "CG-2E8F3CC8A8EBCDE6B7CF4D27";
            attribute connectionType : String = "SIGNAL";
            attribute originalPath : String = "D113::PORT::D113::牵引指令输出::ITM-CMD-002::输出 -> 8121::PORT::8121::牵引指令输入::ITM-CMD-002::输入";
        }
        interface c_CG_2EE117B4B0633E38D394B904 : IF_IF_CMD_018 connect p_N_4000.p_N_4200.p_N_4230.p_N_4238.rp_9744a4b3a255a6e8 to p_N_4000.p_N_4100.p_N_4110.p_N_411C.rp_201c13a158f19a88 {
            attribute connectionId : String = "CG-2EE117B4B0633E38D394B904";
            attribute connectionType : String = "SIGNAL";
            attribute originalPath : String = "4238::PORT::4238::受电弓控制指令输出::ITM-CMD-018::输出 -> 411C::PORT::411C::受电弓控制指令输入::ITM-CMD-018::输入";
        }
        interface c_CG_3352802713B03806EB2934A1 : IF_IF_STA_025 connect p_N_8000.p_N_8100.p_N_8120.p_N_8128.rp_9f2f985b6764bfa7 to p_N_8000.p_N_8100.p_N_8120.p_N_8121.rp_36991cec1f7be17b {
            attribute connectionId : String = "CG-3352802713B03806EB2934A1";
            attribute connectionType : String = "SIGNAL";
            attribute originalPath : String = "8128::PORT::8128::制动安全回路状态输出::ITM-STA-025::输出 -> 8121::PORT::8121::制动安全回路状态输入::ITM-STA-025::输入";
        }
        interface c_CG_338D68ABEF709ACD5E0DDCC6 : IF_IF_PHY_005 connect p_N_5000.p_N_5300.p_N_5310.p_N_5311.rp_97eb613c06ae1b2e to p_N_3000.p_N_3500.p_N_3510.p_N_3511.rp_aa7691c6f81e4771 {
            attribute connectionId : String = "CG-338D68ABEF709ACD5E0DDCC6";
            attribute connectionType : String = "SERIES";
            attribute originalPath : String = "5311::PORT::5311::旋转机械能端口::ITM-PHY-005::双向物理 -> 3511::PORT::3511::第一连接面旋转机械能端口::ITM-PHY-005::双向物理";
        }
        interface c_CG_3632726B793CD5429112CAD4 : IF_IF_PHY_001 connect p_N_4000.p_N_4200.p_N_4210.p_N_4211.rp_ee92cd728b152a90 to p_N_4000.p_N_4200.p_N_4210.p_N_4212.rp_4b65d610848833a3 {
            attribute connectionId : String = "CG-3632726B793CD5429112CAD4";
            attribute connectionType : String = "SERIES";
            attribute originalPath : String = "4211::PORT::4211::出线侧高压交流电能端口::ITM-PHY-001::双向物理 -> 4212::PORT::4212::进线侧高压交流电能端口::ITM-PHY-001::双向物理";
        }
        interface c_CG_37792F42F4274C7C51C63270 : IF_IF_STA_013 connect p_N_4000.p_N_4200.p_N_4230.p_N_4238.rp_0674d2b80a6a72da to p_N_4000.p_N_4500.p_N_4510.p_N_4518.rp_67eef246e016ac82 {
            attribute connectionId : String = "CG-37792F42F4274C7C51C63270";
            attribute connectionType : String = "SIGNAL";
            attribute originalPath : String = "4238::PORT::4238::高压断路器状态输出::ITM-STA-013::输出 -> 4518::PORT::4518::高压断路器状态输入::ITM-STA-013::输入";
        }
        interface c_CG_37ECA5B04E215AC3E6A4B472 : IF_IF_MEA_011 connect p_N_5000.p_N_5300.p_N_5310.p_N_5311.rp_537e9856bafa2a02 to p_N_5000.p_N_5100.p_N_5110.p_N_5112.rp_21e86fb073b61523 {
            attribute connectionId : String = "CG-37ECA5B04E215AC3E6A4B472";
            attribute connectionType : String = "SIGNAL";
            attribute originalPath : String = "5311::PORT::5311::电机侧相电压输出::ITM-MEA-011::输出 -> 5112::PORT::5112::电机侧相电压输入::ITM-MEA-011::输入";
        }
        interface c_CG_3981A8B947B66F597AA9E03F : IF_IF_CMD_020 connect p_N_7000.p_N_7200.p_N_7210.p_N_7211.rp_a882b33038ce4623 to p_N_7000.p_N_7200.p_N_7280.p_N_7285.rp_c016d56a46e739fc {
            attribute connectionId : String = "CG-3981A8B947B66F597AA9E03F";
            attribute connectionType : String = "SIGNAL";
            attribute originalPath : String = "7211::PORT::7211::制动隔离指令输出::ITM-CMD-020::输出 -> 7285::PORT::7285::制动隔离指令输入::ITM-CMD-020::输入";
        }
        interface c_CG_3BD24EBE88F37EEFFE563597 : IF_IF_PHY_004 connect p_N_5000.p_N_5100.p_N_5130.p_N_5132.rp_770f7e1c507cc073 to p_N_5000.p_N_5300.p_N_5310.p_N_5311.rp_57f3c317ac0c860d {
            attribute connectionId : String = "CG-3BD24EBE88F37EEFFE563597";
            attribute connectionType : String = "SERIES";
            attribute originalPath : String = "5132::PORT::5132::三相交流电能端口::ITM-PHY-004::双向物理 -> 5311::PORT::5311::三相交流电能端口::ITM-PHY-004::双向物理";
        }
        interface c_CG_3BE61F5C037C7491E88F4334 : IF_IF_CMD_015 connect p_N_5000.p_N_5100.p_N_5140.p_N_5145.rp_e58f80e07056f3fb to p_N_5000.p_N_5100.p_N_5130.p_N_5133.rp_77ee52e55ac1ca4e {
            attribute connectionId : String = "CG-3BE61F5C037C7491E88F4334";
            attribute connectionType : String = "SIGNAL";
            attribute originalPath : String = "5145::PORT::5145::制动斩波器指令输出::ITM-CMD-015::输出 -> 5133::PORT::5133::制动斩波器指令输入::ITM-CMD-015::输入";
        }
        interface c_CG_3CA6C3BF7D7B4F80CF0990D0 : IF_IF_PHY_005 connect p_N_3000.p_N_3500.p_N_3510.p_N_3512.rp_c455741f6ca5a597 to p_N_3000.p_N_3100.p_N_3120.p_N_3121.rp_fdcd27ee9b0a936f {
            attribute connectionId : String = "CG-3CA6C3BF7D7B4F80CF0990D0";
            attribute connectionType : String = "SERIES";
            attribute originalPath : String = "3512::PORT::3512::第二连接面旋转机械能端口::ITM-PHY-005::双向物理 -> 3121::PORT::3121::高速轴旋转机械能端口::ITM-PHY-005::双向物理";
        }
        interface c_CG_40ADD911FF2840BEEAA67F8D : IF_IF_ACC_002 connect p_N_5000.p_N_5100.p_N_5130.p_N_5132.rp_75d86c9dc39b94b8 to p_N_8000.p_N_8100.p_N_8120.p_N_8122.rp_bd78e8d84d334672 {
            attribute connectionId : String = "CG-40ADD911FF2840BEEAA67F8D";
            attribute connectionType : String = "SIGNAL";
            attribute originalPath : String = "5132::PORT::5132::实际再生功率输出::ITM-ACC-002::输出 -> 8122::PORT::8122::实际再生功率输入::ITM-ACC-002::输入";
        }
        interface c_CG_4104726E8B8410405C176AF3 : IF_IF_CMD_017 connect p_N_4000.p_N_4200.p_N_4230.p_N_4238.rp_ed1efa73e618c52f to p_N_4000.p_N_4200.p_N_4210.p_N_4212.rp_a29d16c43fc8d044 {
            attribute connectionId : String = "CG-4104726E8B8410405C176AF3";
            attribute connectionType : String = "SIGNAL";
            attribute originalPath : String = "4238::PORT::4238::高压隔离开关指令输出::ITM-CMD-017::输出 -> 4212::PORT::4212::高压隔离开关指令输入::ITM-CMD-017::输入";
        }
        interface c_CG_410B8D702206200512DD3731 : IF_IF_CMD_003 connect p_N_8000.p_N_8100.p_N_8120.p_N_8121.rp_d82e5c8a7afb4b7b to p_N_8000.p_N_8100.p_N_8120.p_N_8122.rp_898e3aba50ea7cb4 {
            attribute connectionId : String = "CG-410B8D702206200512DD3731";
            attribute connectionType : String = "SIGNAL";
            attribute originalPath : String = "8121::PORT::8121::服务制动请求输出::ITM-CMD-003::输出 -> 8122::PORT::8122::服务制动请求输入::ITM-CMD-003::输入";
        }
        interface c_CG_4163C3EB1F2D16B7AFCB21C9 : IF_IF_CMD_004 connect p_N_8000.p_N_8100.p_N_8120.p_N_8121.rp_a9c7eff84933cd80 to p_N_7000.p_N_7200.p_N_7220.p_N_7226.rp_5f6a9d81cebde2d3 {
            attribute connectionId : String = "CG-4163C3EB1F2D16B7AFCB21C9";
            attribute connectionType : String = "SIGNAL";
            attribute originalPath : String = "8121::PORT::8121::紧急制动请求输出::ITM-CMD-004::输出 -> 7226::PORT::7226::紧急制动请求输入::ITM-CMD-004::输入";
        }
        interface c_CG_41AD09EEB4EAB9DC956C08F8 : IF_IF_CMD_003 connect p_D000.p_D100.p_D110.p_D114.rp_d3d5739989ecf2dd to p_N_8000.p_N_8100.p_N_8120.p_N_8121.rp_0b58c63caeaf2f6d {
            attribute connectionId : String = "CG-41AD09EEB4EAB9DC956C08F8";
            attribute connectionType : String = "SIGNAL";
            attribute originalPath : String = "D114::PORT::D114::服务制动请求输出::ITM-CMD-003::输出 -> 8121::PORT::8121::服务制动请求输入::ITM-CMD-003::输入";
        }
        interface c_CG_43EF4A944142319DE5088758 : IF_IF_MEA_006 connect p_N_4000.p_N_4200.p_N_4230.p_N_4238.rp_c7dcc306b020116f to p_N_4000.p_N_4200.p_N_4240.p_N_4241.rp_f81c0f4a108acec4 {
            attribute connectionId : String = "CG-43EF4A944142319DE5088758";
            attribute connectionType : String = "SIGNAL";
            attribute originalPath : String = "4238::PORT::4238::高压线路电流输出::ITM-MEA-006::输出 -> 4241::PORT::4241::高压线路电流输入::ITM-MEA-006::输入";
        }
        interface c_CG_44890BAD0E32A867EFFB7EBB : IF_IF_STA_026 connect p_N_8000.p_N_8100.p_N_8150.p_N_8154.rp_492d0ced994652db to p_N_8000.p_N_8100.p_N_8120.p_N_8128.rp_9819959a053f9c06 {
            attribute connectionId : String = "CG-44890BAD0E32A867EFFB7EBB";
            attribute connectionType : String = "SIGNAL";
            attribute originalPath : String = "8154::PORT::8154::牵引安全回路状态输出::ITM-STA-026::输出 -> 8128::PORT::8128::牵引安全回路状态输入::ITM-STA-026::输入";
        }
        interface c_CG_44E8AB4EA7ED953642770E4E : IF_IF_CMD_009 connect p_N_8000.p_N_8100.p_N_8120.p_N_8121.rp_f4c8eaaf49d11d3d to p_N_8000.p_N_8100.p_N_8120.p_N_8125.rp_0e01f3a589418f6c {
            attribute connectionId : String = "CG-44E8AB4EA7ED953642770E4E";
            attribute connectionType : String = "SIGNAL";
            attribute originalPath : String = "8121::PORT::8121::牵引使能指令输出::ITM-CMD-009::输出 -> 8125::PORT::8125::牵引使能指令输入::ITM-CMD-009::输入";
        }
        interface c_CG_464B2D6F08DDD0D4287D0294 : IF_IF_STA_026 connect p_N_8000.p_N_8100.p_N_8120.p_N_8128.rp_aad98cbe8fa3b27e to p_N_8000.p_N_8100.p_N_8120.p_N_8125.rp_90deb6e5a4e470f1 {
            attribute connectionId : String = "CG-464B2D6F08DDD0D4287D0294";
            attribute connectionType : String = "SIGNAL";
            attribute originalPath : String = "8128::PORT::8128::牵引安全回路状态输出::ITM-STA-026::输出 -> 8125::PORT::8125::牵引安全回路状态输入::ITM-STA-026::输入";
        }
        interface c_CG_46A1EE350324445D016EAF45 : IF_IF_MEA_004 connect p_N_5000.p_N_5300.p_N_5310.p_N_5311.rp_79c695a1342df24f to p_N_5000.p_N_5100.p_N_5110.p_N_5112.rp_780596fabcc73a0f {
            attribute connectionId : String = "CG-46A1EE350324445D016EAF45";
            attribute connectionType : String = "SIGNAL";
            attribute originalPath : String = "5311::PORT::5311::牵引电机转速输出::ITM-MEA-004::输出 -> 5112::PORT::5112::牵引电机转速输入::ITM-MEA-004::输入";
        }
        interface c_CG_48B77E7B4DEB11D4F5543CCB : IF_IF_PHY_011 connect p_N_4000.p_N_4400.p_N_4410.p_N_4413.rp_cb582bd13ed15889 to boundary_BOUNDARY_RAIL.bp_3a29560c03050dbe {
            attribute connectionId : String = "CG-48B77E7B4DEB11D4F5543CCB";
            attribute connectionType : String = "BOUNDARY";
            attribute originalPath : String = "4413::PORT::4413::固定端回流电流端口::ITM-PHY-011::双向物理 -> BOUNDARY-RAIL::BPORT::BOUNDARY-RAIL::ITM-PHY-011";
        }
        interface c_CG_4B59832BB120B07245DB82FA : IF_IF_PHY_005 connect p_N_3000.p_N_3500.p_N_3510.p_N_3511.rp_813a305545723d57 to p_N_3000.p_N_3500.p_N_3510.p_N_3514.rp_b12dc4cc17618821 {
            attribute connectionId : String = "CG-4B59832BB120B07245DB82FA";
            attribute connectionType : String = "SERIES";
            attribute originalPath : String = "3511::PORT::3511::第二连接面旋转机械能端口::ITM-PHY-005::双向物理 -> 3514::PORT::3514::第一轴端旋转机械能端口::ITM-PHY-005::双向物理";
        }
        interface c_CG_4CB0735167799FD438F90DD2 : IF_IF_PHY_005 connect p_N_3000.p_N_3600.p_N_3640.p_N_3643.rp_48ddc723a7d58137 to p_N_3000.p_N_3100.p_N_3120.p_N_3121.rp_6464b6253314b208 {
            attribute connectionId : String = "CG-4CB0735167799FD438F90DD2";
            attribute connectionType : String = "TAP";
            attribute originalPath : String = "3643::PORT::3643::旋转机械能端口::ITM-PHY-005::双向物理 -> 3121::PORT::3121::低速轴旋转机械能端口::ITM-PHY-005::双向物理";
        }
        interface c_CG_4DBAA813D3DED180F94E9B7F : IF_IF_PHY_014 connect p_N_5000.p_N_5100.p_N_5120.p_N_5121.rp_9dedfe88c8a34261 to p_N_5000.p_N_5100.p_N_5130.p_N_5131.rp_32d77ca0c1d88b50 {
            attribute connectionId : String = "CG-4DBAA813D3DED180F94E9B7F";
            attribute connectionType : String = "SERIES";
            attribute originalPath : String = "5121::PORT::5121::牵引变压器次级交流电能端口::ITM-PHY-014::双向物理 -> 5131::PORT::5131::牵引变压器次级交流电能端口::ITM-PHY-014::双向物理";
        }
        interface c_CG_4E4C49F08CEE642A5C3C67EB : IF_IF_MEA_009 connect p_N_5000.p_N_5100.p_N_5140.p_N_5145.rp_a9cc4822e30a5ede to p_N_8000.p_N_8100.p_N_8160.p_N_8166.rp_3b0068559b0ca1e4 {
            attribute connectionId : String = "CG-4E4C49F08CEE642A5C3C67EB";
            attribute connectionType : String = "SIGNAL";
            attribute originalPath : String = "5145::PORT::5145::中间直流母线电流输出::ITM-MEA-009::输出 -> 8166::PORT::8166::中间直流母线电流输入::ITM-MEA-009::输入";
        }
        interface c_CG_50AB5ECD4830D34487B7B557 : IF_IF_CMD_008 connect p_N_8000.p_N_8100.p_N_8120.p_N_8121.rp_c49f12594ff56025 to p_N_8000.p_N_8100.p_N_8150.p_N_8154.rp_a8fff2340df81262 {
            attribute connectionId : String = "CG-50AB5ECD4830D34487B7B557";
            attribute connectionType : String = "SIGNAL";
            attribute originalPath : String = "8121::PORT::8121::牵引切除请求输出::ITM-CMD-008::输出 -> 8154::PORT::8154::牵引切除请求输入::ITM-CMD-008::输入";
        }
        interface c_CG_51C22959FEAD177C3827B364 : IF_IF_PHY_001 connect p_N_4000.p_N_4200.p_N_4230.p_N_4235.rp_3e2b71c6b8d79136 to p_N_4000.p_N_4200.p_N_4210.p_N_4212.rp_e1689d643b97d378 {
            attribute connectionId : String = "CG-51C22959FEAD177C3827B364";
            attribute connectionType : String = "TAP";
            attribute originalPath : String = "4235::PORT::4235::高压交流电能端口::ITM-PHY-001::双向物理 -> 4212::PORT::4212::出线侧高压交流电能端口::ITM-PHY-001::双向物理";
        }
        interface c_CG_53ADA5E90929843D3AD53312 : IF_IF_CMD_024 connect p_N_8000.p_N_8100.p_N_8120.p_N_8122.rp_f0886e48bf75472f to p_N_8000.p_N_8100.p_N_8120.p_N_8128.rp_26589bfc82ed6979 {
            attribute connectionId : String = "CG-53ADA5E90929843D3AD53312";
            attribute connectionType : String = "SIGNAL";
            attribute originalPath : String = "8122::PORT::8122::撒砂请求输出::ITM-CMD-024::输出 -> 8128::PORT::8128::撒砂请求输入::ITM-CMD-024::输入";
        }
        interface c_CG_55513667B46680F5B87A0939 : IF_IF_STA_019 connect p_N_5000.p_N_5100.p_N_5110.p_N_5113.rp_d93ff3dea2be11bd to p_N_8000.p_N_8100.p_N_8120.p_N_8122.rp_81e596aab3f0fe4c {
            attribute connectionId : String = "CG-55513667B46680F5B87A0939";
            attribute connectionType : String = "SIGNAL";
            attribute originalPath : String = "5113::PORT::5113::牵引变流器故障状态输出::ITM-STA-019::输出 -> 8122::PORT::8122::牵引变流器故障状态输入::ITM-STA-019::输入";
        }
        interface c_CG_565AF053FC6E3FF333FD7433 : IF_IF_CMD_024 connect p_N_8000.p_N_8100.p_N_8120.p_N_8128.rp_5accd69f9c3a8b0c to p_N_3000.p_N_3800.p_N_3810.p_N_3811.rp_81d4e1a7092e0653 {
            attribute connectionId : String = "CG-565AF053FC6E3FF333FD7433";
            attribute connectionType : String = "SIGNAL";
            attribute originalPath : String = "8128::PORT::8128::撒砂请求输出::ITM-CMD-024::输出 -> 3811::PORT::3811::撒砂请求输入::ITM-CMD-024::输入";
        }
        interface c_CG_56E4DA6D8C7C1FCFA93A8C7B : IF_IF_CMD_023 connect p_N_7000.p_N_7200.p_N_7210.p_N_7211.rp_91854864e6254d28 to p_N_7000.p_N_7200.p_N_7220.p_N_722A.rp_afe779aaa3b0be62 {
            attribute connectionId : String = "CG-56E4DA6D8C7C1FCFA93A8C7B";
            attribute connectionType : String = "SIGNAL";
            attribute originalPath : String = "7211::PORT::7211::防滑干预指令输出::ITM-CMD-023::输出 -> 722A::PORT::722A::防滑干预指令输入::ITM-CMD-023::输入";
        }
        interface c_CG_57C4C380DFA4E14C0890F4FC : IF_IF_MEA_008 connect p_N_5000.p_N_5100.p_N_5140.p_N_5145.rp_1680714c67f7d311 to p_N_5000.p_N_5100.p_N_5110.p_N_5111.rp_a9ddcab662f35564 {
            attribute connectionId : String = "CG-57C4C380DFA4E14C0890F4FC";
            attribute connectionType : String = "SIGNAL";
            attribute originalPath : String = "5145::PORT::5145::中间直流母线电压输出::ITM-MEA-008::输出 -> 5111::PORT::5111::中间直流母线电压输入::ITM-MEA-008::输入";
        }
        interface c_CG_585503C9572B9BF371266D8B : IF_IF_PHY_013 connect p_X000.p_X100.p_X120.p_X121.rp_387cdae1b4483182 to boundary_BOUNDARY_THERMAL_ENVIRONMENT.bp_2ac3a221090b246a {
            attribute connectionId : String = "CG-585503C9572B9BF371266D8B";
            attribute connectionType : String = "BOUNDARY";
            attribute originalPath : String = "X121::PORT::X121::热能_热流端口::ITM-PHY-013::双向物理 -> BOUNDARY-THERMAL-ENVIRONMENT::BPORT::BOUNDARY-THERMAL-ENVIRONMENT::ITM-PHY-013";
        }
        interface c_CG_5CC6DABFA52A640C8BC115E5 : IF_IF_PHY_005 connect p_N_3000.p_N_3500.p_N_3510.p_N_3514.rp_4569aa8f56963dc6 to p_N_3000.p_N_3500.p_N_3510.p_N_3512.rp_970ef7da9f850ce1 {
            attribute connectionId : String = "CG-5CC6DABFA52A640C8BC115E5";
            attribute connectionType : String = "SERIES";
            attribute originalPath : String = "3514::PORT::3514::第二轴端旋转机械能端口::ITM-PHY-005::双向物理 -> 3512::PORT::3512::第一连接面旋转机械能端口::ITM-PHY-005::双向物理";
        }
        interface c_CG_5E309780F220E97DE29B2A38 : IF_IF_STA_009 connect p_N_7000.p_N_7200.p_N_7220.p_N_722C.rp_6f3dd380decaae91 to p_N_7000.p_N_7200.p_N_7210.p_N_7211.rp_19f11c6ee3cbf055 {
            attribute connectionId : String = "CG-5E309780F220E97DE29B2A38";
            attribute connectionType : String = "SIGNAL";
            attribute originalPath : String = "722C::PORT::722C::低风压状态输出::ITM-STA-009::输出 -> 7211::PORT::7211::低风压状态输入::ITM-STA-009::输入";
        }
        interface c_CG_61CA88D0219D5B46EEFA0E92 : IF_IF_CMD_026 connect p_X000.p_X100.p_X110.p_X112.rp_f980a38f780089b6 to p_X000.p_X100.p_X110.p_X111.rp_6085b3266f1baf9d {
            attribute connectionId : String = "CG-61CA88D0219D5B46EEFA0E92";
            attribute connectionType : String = "SIGNAL";
            attribute originalPath : String = "X112::PORT::X112::双向DC_DC使能输出::ITM-CMD-026::输出 -> X111::PORT::X111::双向DC_DC使能输入::ITM-CMD-026::输入";
        }
        interface c_CG_62B37C74D7B0F1346E00D437 : IF_IF_CMD_011 connect p_N_5000.p_N_5100.p_N_5110.p_N_5112.rp_c98f6aa887541378 to p_N_5000.p_N_5100.p_N_5130.p_N_5132.rp_406d292901368d53 {
            attribute connectionId : String = "CG-62B37C74D7B0F1346E00D437";
            attribute connectionType : String = "SIGNAL";
            attribute originalPath : String = "5112::PORT::5112::电机侧变流控制指令输出::ITM-CMD-011::输出 -> 5132::PORT::5132::电机侧变流控制指令输入::ITM-CMD-011::输入";
        }
        interface c_CG_6546CFCB7800C785459AC8E1 : IF_IF_STA_026 connect p_N_8000.p_N_8100.p_N_8120.p_N_8128.rp_aad98cbe8fa3b27e to p_N_8000.p_N_8100.p_N_8120.p_N_8121.rp_de2d35d2bcb08b0b {
            attribute connectionId : String = "CG-6546CFCB7800C785459AC8E1";
            attribute connectionType : String = "SIGNAL";
            attribute originalPath : String = "8128::PORT::8128::牵引安全回路状态输出::ITM-STA-026::输出 -> 8121::PORT::8121::牵引安全回路状态输入::ITM-STA-026::输入";
        }
        interface c_CG_65E377DBF988541FA5778D1E : IF_IF_MEA_012 connect p_N_5000.p_N_5300.p_N_5310.p_N_5311.rp_10bb4c4f0063bc18 to p_N_8000.p_N_8100.p_N_8120.p_N_8125.rp_1faca3fc4ff0e741 {
            attribute connectionId : String = "CG-65E377DBF988541FA5778D1E";
            attribute connectionType : String = "SIGNAL";
            attribute originalPath : String = "5311::PORT::5311::牵引电机实际转矩输出::ITM-MEA-012::输出 -> 8125::PORT::8125::牵引电机实际转矩输入::ITM-MEA-012::输入";
        }
        interface c_CG_663CDC611495882DCD3E5B8F : IF_IF_CMD_004 connect p_D000.p_D100.p_D120.p_D121.rp_d32b32814a84a88a to p_N_8000.p_N_8100.p_N_8150.p_N_8152.rp_93024c6ed1623fbd {
            attribute connectionId : String = "CG-663CDC611495882DCD3E5B8F";
            attribute connectionType : String = "SIGNAL";
            attribute originalPath : String = "D121::PORT::D121::紧急制动请求输出::ITM-CMD-004::输出 -> 8152::PORT::8152::紧急制动请求输入::ITM-CMD-004::输入";
        }
        interface c_CG_676A4A51307B0199D39544B7 : IF_IF_CMD_017 connect p_N_4000.p_N_4200.p_N_4230.p_N_4239.rp_e30c550b4d4e8d52 to p_N_4000.p_N_4200.p_N_4230.p_N_4238.rp_f6362be8ea9a501f {
            attribute connectionId : String = "CG-676A4A51307B0199D39544B7";
            attribute connectionType : String = "SIGNAL";
            attribute originalPath : String = "4239::PORT::4239::高压隔离开关指令输出::ITM-CMD-017::输出 -> 4238::PORT::4238::高压隔离开关指令输入::ITM-CMD-017::输入";
        }
        interface c_CG_686A357580FCAB93907E7B31 : IF_IF_PHY_007 connect p_N_7000.p_N_7200.p_N_7250.p_N_7252.rp_b403e112a25e1c53 to p_N_7000.p_N_7200.p_N_7250.p_N_7254.rp_d9511ef0fa1c17df {
            attribute connectionId : String = "CG-686A357580FCAB93907E7B31";
            attribute connectionType : String = "SERIES";
            attribute originalPath : String = "7252::PORT::7252::摩擦制动机械作用端口::ITM-PHY-007::双向物理 -> 7254::PORT::7254::摩擦制动机械作用端口::ITM-PHY-007::双向物理";
        }
        interface c_CG_686E1C0741D80B3DE2EEBA80 : IF_IF_MEA_008 connect p_X000.p_X100.p_X110.p_X113.rp_0e45c7ab357a42e6 to p_X000.p_X100.p_X110.p_X112.rp_89849c49127b2dfb {
            attribute connectionId : String = "CG-686E1C0741D80B3DE2EEBA80";
            attribute connectionType : String = "SIGNAL";
            attribute originalPath : String = "X113::PORT::X113::中间直流母线电压输出::ITM-MEA-008::输出 -> X112::PORT::X112::中间直流母线电压输入::ITM-MEA-008::输入";
        }
        interface c_CG_697084EEC1DCA9E975638C14 : IF_IF_CMD_030 connect p_N_8000.p_N_8100.p_N_8120.p_N_8127.rp_8f3091a86214dd4e to p_N_8000.p_N_8100.p_N_8150.p_N_8152.rp_1e4f882572b04df5 {
            attribute connectionId : String = "CG-697084EEC1DCA9E975638C14";
            attribute connectionType : String = "SIGNAL";
            attribute originalPath : String = "8127::PORT::8127::安全停车_制动请求输出::ITM-CMD-030::输出 -> 8152::PORT::8152::安全停车_制动请求输入::ITM-CMD-030::输入";
        }
        interface c_CG_6C6B569AD3F71A70A799D067 : IF_IF_MEA_005 connect p_N_4000.p_N_4200.p_N_4230.p_N_4238.rp_5576b5e0dbb912ba to p_N_4000.p_N_4200.p_N_4230.p_N_4239.rp_2802b0f2f54a548a {
            attribute connectionId : String = "CG-6C6B569AD3F71A70A799D067";
            attribute connectionType : String = "SIGNAL";
            attribute originalPath : String = "4238::PORT::4238::高压线路电压输出::ITM-MEA-005::输出 -> 4239::PORT::4239::高压线路电压输入::ITM-MEA-005::输入";
        }
        interface c_CG_70D940D7F34BF27762FED746 : IF_IF_STA_024 connect p_N_8000.p_N_8100.p_N_8150.p_N_8151.rp_c6902e30a0122c0e to p_N_8000.p_N_8100.p_N_8120.p_N_8128.rp_2b9604597ff0c9ac {
            attribute connectionId : String = "CG-70D940D7F34BF27762FED746";
            attribute connectionType : String = "SIGNAL";
            attribute originalPath : String = "8151::PORT::8151::高压安全回路状态输出::ITM-STA-024::输出 -> 8128::PORT::8128::高压安全回路状态输入::ITM-STA-024::输入";
        }
        interface c_CG_732BB9F5922B7AC9420BB2D0 : IF_IF_MEA_008 connect p_N_5000.p_N_5100.p_N_5140.p_N_5145.rp_1680714c67f7d311 to p_N_8000.p_N_8100.p_N_8120.p_N_8122.rp_361eac651ec9fd05 {
            attribute connectionId : String = "CG-732BB9F5922B7AC9420BB2D0";
            attribute connectionType : String = "SIGNAL";
            attribute originalPath : String = "5145::PORT::5145::中间直流母线电压输出::ITM-MEA-008::输出 -> 8122::PORT::8122::中间直流母线电压输入::ITM-MEA-008::输入";
        }
        interface c_CG_734E10C63B7A36C2BB06360D : IF_IF_STA_033 connect p_X000.p_X100.p_X130.p_X132.rp_53191daa39f85d49 to p_X000.p_X100.p_X110.p_X112.rp_3ecd9966c9972a7e {
            attribute connectionId : String = "CG-734E10C63B7A36C2BB06360D";
            attribute connectionType : String = "SIGNAL";
            attribute originalPath : String = "X132::PORT::X132::储能预充电状态输出::ITM-STA-033::输出 -> X112::PORT::X112::储能预充电状态输入::ITM-STA-033::输入";
        }
        interface c_CG_7365C853DD9391D9914E0C8A : IF_IF_CMD_012 connect p_N_8000.p_N_8100.p_N_8120.p_N_8125.rp_70a8e2c4b0887b4d to p_N_5000.p_N_5100.p_N_5110.p_N_5112.rp_6ce5fb5c81d47ab4 {
            attribute connectionId : String = "CG-7365C853DD9391D9914E0C8A";
            attribute connectionType : String = "SIGNAL";
            attribute originalPath : String = "8125::PORT::8125::牵引电机转矩请求输出::ITM-CMD-012::输出 -> 5112::PORT::5112::牵引电机转矩请求输入::ITM-CMD-012::输入";
        }
        interface c_CG_739E53DD845C8CD2646C8E39 : IF_IF_MEA_014 connect p_N_7000.p_N_7100.p_N_7140.p_N_7142.rp_52f3b82b80918b84 to p_N_8000.p_N_8100.p_N_8120.p_N_8128.rp_ccc90acd04ba0ccc {
            attribute connectionId : String = "CG-739E53DD845C8CD2646C8E39";
            attribute connectionType : String = "SIGNAL";
            attribute originalPath : String = "7142::PORT::7142::总风管压力输出::ITM-MEA-014::输出 -> 8128::PORT::8128::总风管压力输入::ITM-MEA-014::输入";
        }
        interface c_CG_76271B14A422D23C0C6E327D : IF_IF_PHY_013 connect p_N_4000.p_N_4400.p_N_4410.p_N_4411.rp_c61d1b462f69be85 to boundary_BOUNDARY_THERMAL_ENVIRONMENT.bp_2ac3a221090b246a {
            attribute connectionId : String = "CG-76271B14A422D23C0C6E327D";
            attribute connectionType : String = "BOUNDARY";
            attribute originalPath : String = "4411::PORT::4411::热能_热流端口::ITM-PHY-013::双向物理 -> BOUNDARY-THERMAL-ENVIRONMENT::BPORT::BOUNDARY-THERMAL-ENVIRONMENT::ITM-PHY-013";
        }
        interface c_CG_7664DA49869213FC03120E3B : IF_IF_MEA_013 connect p_N_8000.p_N_8100.p_N_8120.p_N_8125.rp_36a59f5828d4c515 to p_N_8000.p_N_8100.p_N_8120.p_N_8122.rp_f36629c6f163833f {
            attribute connectionId : String = "CG-7664DA49869213FC03120E3B";
            attribute connectionType : String = "SIGNAL";
            attribute originalPath : String = "8125::PORT::8125::实际动态制动力输出::ITM-MEA-013::输出 -> 8122::PORT::8122::实际动态制动力输入::ITM-MEA-013::输入";
        }
        interface c_CG_767F79CB763B96968C94D7AD : IF_IF_CMD_001 connect p_N_8000.p_N_8100.p_N_8120.p_N_8121.rp_8fbe2a98ba0ac28c to p_N_8000.p_N_8100.p_N_8120.p_N_8122.rp_ac60006ecd824aae {
            attribute connectionId : String = "CG-767F79CB763B96968C94D7AD";
            attribute connectionType : String = "SIGNAL";
            attribute originalPath : String = "8121::PORT::8121::列车方向指令输出::ITM-CMD-001::输出 -> 8122::PORT::8122::列车方向指令输入::ITM-CMD-001::输入";
        }
        interface c_CG_79EB6BEB9B0AE9B2B06844A4 : IF_IF_CMD_027 connect p_X000.p_X100.p_X110.p_X112.rp_2ea4241545e6ca09 to p_X000.p_X100.p_X130.p_X131.rp_b06975e1baff62be {
            attribute connectionId : String = "CG-79EB6BEB9B0AE9B2B06844A4";
            attribute connectionType : String = "SIGNAL";
            attribute originalPath : String = "X112::PORT::X112::储能主接触器指令输出::ITM-CMD-027::输出 -> X131::PORT::X131::储能主接触器指令输入::ITM-CMD-027::输入";
        }
        interface c_CG_7A2381DC8C36A40B747035A5 : IF_IF_CMD_025 connect p_N_8000.p_N_8100.p_N_8120.p_N_8122.rp_77c439392dea95b4 to p_X000.p_X100.p_X110.p_X112.rp_843fa8c83311440e {
            attribute connectionId : String = "CG-7A2381DC8C36A40B747035A5";
            attribute connectionType : String = "SIGNAL";
            attribute originalPath : String = "8122::PORT::8122::储能功率请求输出::ITM-CMD-025::输出 -> X112::PORT::X112::储能功率请求输入::ITM-CMD-025::输入";
        }
        interface c_CG_7AAA105058D4FD893E634E16 : IF_IF_STA_004 connect p_N_7000.p_N_7200.p_N_7210.p_N_7211.rp_77f0053899ab19da to p_N_7000.p_N_7200.p_N_7280.p_N_7281.rp_b9ead4720ad37cb5 {
            attribute connectionId : String = "CG-7AAA105058D4FD893E634E16";
            attribute connectionType : String = "SIGNAL";
            attribute originalPath : String = "7211::PORT::7211::制动施加状态输出::ITM-STA-004::输出 -> 7281::PORT::7281::制动施加状态输入::ITM-STA-004::输入";
        }
        interface c_CG_7AEA5BA2801064550BBE6D02 : IF_IF_CMD_002 connect p_N_8000.p_N_8100.p_N_8120.p_N_8121.rp_809f8275c004ab18 to p_N_8000.p_N_8100.p_N_8120.p_N_8125.rp_713c697d47d94da9 {
            attribute connectionId : String = "CG-7AEA5BA2801064550BBE6D02";
            attribute connectionType : String = "SIGNAL";
            attribute originalPath : String = "8121::PORT::8121::牵引指令输出::ITM-CMD-002::输出 -> 8125::PORT::8125::牵引指令输入::ITM-CMD-002::输入";
        }
        interface c_CG_7CA35F612B7EF59664CE06F0 : IF_IF_PHY_013 connect p_N_3000.p_N_3100.p_N_3130.p_N_3132.rp_6069e8d0fbf298c5 to boundary_BOUNDARY_THERMAL_ENVIRONMENT.bp_2ac3a221090b246a {
            attribute connectionId : String = "CG-7CA35F612B7EF59664CE06F0";
            attribute connectionType : String = "BOUNDARY";
            attribute originalPath : String = "3132::PORT::3132::热能_热流端口::ITM-PHY-013::双向物理 -> BOUNDARY-THERMAL-ENVIRONMENT::BPORT::BOUNDARY-THERMAL-ENVIRONMENT::ITM-PHY-013";
        }
        interface c_CG_7D415C2FE2A98E99E69F2808 : IF_IF_PHY_007 connect p_N_7000.p_N_7200.p_N_7250.p_N_7255.rp_4c45e349056154be to p_N_7000.p_N_7200.p_N_7250.p_N_7252.rp_b403e112a25e1c53 {
            attribute connectionId : String = "CG-7D415C2FE2A98E99E69F2808";
            attribute connectionType : String = "SERIES";
            attribute originalPath : String = "7255::PORT::7255::摩擦制动机械作用端口::ITM-PHY-007::双向物理 -> 7252::PORT::7252::摩擦制动机械作用端口::ITM-PHY-007::双向物理";
        }
        interface c_CG_86987C60BCB826208FEFEF31 : IF_IF_CMD_030 connect p_E000.p_E100.rp_7273a171b473f816 to p_N_8000.p_N_8100.p_N_8120.p_N_8127.rp_be0fc7194a7f0161 {
            attribute connectionId : String = "CG-86987C60BCB826208FEFEF31";
            attribute connectionType : String = "SIGNAL";
            attribute originalPath : String = "E100::PORT::E100::安全停车_制动请求输出::ITM-CMD-030::输出 -> 8127::PORT::8127::安全停车_制动请求输入::ITM-CMD-030::输入";
        }
        interface c_CG_86C48EA2DE057325EEB9853C : IF_IF_MEA_026 connect p_X000.p_X100.p_X120.p_X123.rp_9b6812b4ca482c66 to p_X000.p_X100.p_X110.p_X112.rp_e8341f592e73af5e {
            attribute connectionId : String = "CG-86C48EA2DE057325EEB9853C";
            attribute connectionType : String = "SIGNAL";
            attribute originalPath : String = "X123::PORT::X123::超级电容电流输出::ITM-MEA-026::输出 -> X112::PORT::X112::超级电容电流输入::ITM-MEA-026::输入";
        }
        interface c_CG_89318B491DF9CED18997C36D : IF_IF_STA_027 connect p_E000.p_E100.rp_0307dc18d9537f9d to p_N_8000.p_N_8100.p_N_8120.p_N_8128.rp_ce6397cb7b81dd94 {
            attribute connectionId : String = "CG-89318B491DF9CED18997C36D";
            attribute connectionType : String = "SIGNAL";
            attribute originalPath : String = "E100::PORT::E100::ATP_外部安全系统状态输出::ITM-STA-027::输出 -> 8128::PORT::8128::ATP_外部安全系统状态输入::ITM-STA-027::输入";
        }
        interface c_CG_89DF67BFD358C3EEF4DB05F2 : IF_IF_MEA_004 connect p_N_3000.p_N_3600.p_N_3640.p_N_3644.rp_08c271db56ce8427 to p_N_8000.p_N_8100.p_N_8120.p_N_8125.rp_4e582bfad9ebbf1d {
            attribute connectionId : String = "CG-89DF67BFD358C3EEF4DB05F2";
            attribute connectionType : String = "SIGNAL";
            attribute originalPath : String = "3644::PORT::3644::牵引电机转速输出::ITM-MEA-004::输出 -> 8125::PORT::8125::牵引电机转速输入::ITM-MEA-004::输入";
        }
        interface c_CG_8E2E18108BE2E7B2FB898537 : IF_IF_STA_015 connect p_N_4000.p_N_4200.p_N_4230.p_N_4238.rp_86fe03530d5b3c05 to p_N_4000.p_N_4200.p_N_4230.p_N_4239.rp_f3be8ead57323593 {
            attribute connectionId : String = "CG-8E2E18108BE2E7B2FB898537";
            attribute connectionType : String = "SIGNAL";
            attribute originalPath : String = "4238::PORT::4238::受电弓状态输出::ITM-STA-015::输出 -> 4239::PORT::4239::受电弓状态输入::ITM-STA-015::输入";
        }
        interface c_CG_8EE395387745CC0A6FB55207 : IF_IF_MEA_005 connect p_N_4000.p_N_4200.p_N_4230.p_N_4235.rp_6fea4b377f978aac to p_N_4000.p_N_4200.p_N_4230.p_N_4238.rp_c88ddcdfe3b55c9e {
            attribute connectionId : String = "CG-8EE395387745CC0A6FB55207";
            attribute connectionType : String = "SIGNAL";
            attribute originalPath : String = "4235::PORT::4235::高压线路电压输出::ITM-MEA-005::输出 -> 4238::PORT::4238::高压线路电压输入::ITM-MEA-005::输入";
        }
        interface c_CG_8EED0159D22D9EDC70A9EA67 : IF_IF_CMD_004 connect p_D000.p_D100.p_D120.p_D121.rp_d32b32814a84a88a to p_N_8000.p_N_8100.p_N_8120.p_N_8121.rp_1e34bb2697325127 {
            attribute connectionId : String = "CG-8EED0159D22D9EDC70A9EA67";
            attribute connectionType : String = "SIGNAL";
            attribute originalPath : String = "D121::PORT::D121::紧急制动请求输出::ITM-CMD-004::输出 -> 8121::PORT::8121::紧急制动请求输入::ITM-CMD-004::输入";
        }
        interface c_CG_8F81398231970DBDB0A7F854 : IF_IF_STA_015 connect p_N_4000.p_N_4100.p_N_4110.p_N_411C.rp_72d2eed2608e1b56 to p_N_4000.p_N_4200.p_N_4230.p_N_4238.rp_d9d25dfbac32d1e3 {
            attribute connectionId : String = "CG-8F81398231970DBDB0A7F854";
            attribute connectionType : String = "SIGNAL";
            attribute originalPath : String = "411C::PORT::411C::受电弓状态输出::ITM-STA-015::输出 -> 4238::PORT::4238::受电弓状态输入::ITM-STA-015::输入";
        }
        interface c_CG_91B4F6F81C7185E848BAF73E : IF_IF_PHY_013 connect p_N_3000.p_N_3100.p_N_3130.p_N_3133.rp_24fa6cb520a8e2e2 to boundary_BOUNDARY_THERMAL_ENVIRONMENT.bp_2ac3a221090b246a {
            attribute connectionId : String = "CG-91B4F6F81C7185E848BAF73E";
            attribute connectionType : String = "BOUNDARY";
            attribute originalPath : String = "3133::PORT::3133::热能_热流端口::ITM-PHY-013::双向物理 -> BOUNDARY-THERMAL-ENVIRONMENT::BPORT::BOUNDARY-THERMAL-ENVIRONMENT::ITM-PHY-013";
        }
        interface c_CG_943AD35B9C94E8B079F6212A : IF_IF_CMD_032 connect p_N_3000.p_N_3800.p_N_3810.p_N_3811.rp_3a8ce42fcde5acd8 to p_N_3000.p_N_3800.p_N_3810.p_N_3813.rp_d951497aaa9989f0 {
            attribute connectionId : String = "CG-943AD35B9C94E8B079F6212A";
            attribute connectionType : String = "SIGNAL";
            attribute originalPath : String = "3811::PORT::3811::撒砂执行指令输出::ITM-CMD-032::输出 -> 3813::PORT::3813::撒砂执行指令输入::ITM-CMD-032::输入";
        }
        interface c_CG_944069F2CBBFA2A01274A9DB : IF_IF_STA_003 connect p_N_7000.p_N_7200.p_N_7210.p_N_7211.rp_c021f63639408eff to p_N_8000.p_N_8100.p_N_8120.p_N_8121.rp_1c14ea3cdc439198 {
            attribute connectionId : String = "CG-944069F2CBBFA2A01274A9DB";
            attribute connectionType : String = "SIGNAL";
            attribute originalPath : String = "7211::PORT::7211::制动系统可用状态输出::ITM-STA-003::输出 -> 8121::PORT::8121::制动系统可用状态输入::ITM-STA-003::输入";
        }
        interface c_CG_9465AAC3F0B0B115DC3EF9FD : IF_IF_MEA_028 connect p_X000.p_X100.p_X120.p_X121.rp_b6cf5a49ced52abf to p_N_8000.p_N_8100.p_N_8120.p_N_8122.rp_6437aa0577c9ccd7 {
            attribute connectionId : String = "CG-9465AAC3F0B0B115DC3EF9FD";
            attribute connectionType : String = "SIGNAL";
            attribute originalPath : String = "X121::PORT::X121::超级电容SOC输出::ITM-MEA-028::输出 -> 8122::PORT::8122::超级电容SOC输入::ITM-MEA-028::输入";
        }
        interface c_CG_9731BEC15024660A6C266D47 : IF_IF_MEA_008 connect p_N_5000.p_N_5100.p_N_5140.p_N_5145.rp_1680714c67f7d311 to p_N_5000.p_N_5100.p_N_5130.p_N_5133.rp_60d9996fadd55bff {
            attribute connectionId : String = "CG-9731BEC15024660A6C266D47";
            attribute connectionType : String = "SIGNAL";
            attribute originalPath : String = "5145::PORT::5145::中间直流母线电压输出::ITM-MEA-008::输出 -> 5133::PORT::5133::中间直流母线电压输入::ITM-MEA-008::输入";
        }
        interface c_CG_979C19823B520B68E370ECB6 : IF_IF_CMD_003 connect p_N_8000.p_N_8100.p_N_8120.p_N_8121.rp_d82e5c8a7afb4b7b to p_N_7000.p_N_7200.p_N_7210.p_N_7211.rp_77afbfa330bfb95e {
            attribute connectionId : String = "CG-979C19823B520B68E370ECB6";
            attribute connectionType : String = "SIGNAL";
            attribute originalPath : String = "8121::PORT::8121::服务制动请求输出::ITM-CMD-003::输出 -> 7211::PORT::7211::服务制动请求输入::ITM-CMD-003::输入";
        }
        interface c_CG_992C677E70DA53B7B40EA26C : IF_IF_PHY_001 connect p_N_4000.p_N_4100.p_N_4110.p_N_4111.rp_695b20573c740008 to boundary_BOUNDARY_CATENARY_25KV.bp_6fe914f662252c4d {
            attribute connectionId : String = "CG-992C677E70DA53B7B40EA26C";
            attribute connectionType : String = "BOUNDARY";
            attribute originalPath : String = "4111::PORT::4111::接触面高压交流电能端口::ITM-PHY-001::双向物理 -> BOUNDARY-CATENARY-25KV::BPORT::BOUNDARY-CATENARY-25KV::ITM-PHY-001";
        }
        interface c_CG_9A05AF4B79F0AC70EEBB8C27 : IF_IF_MEA_025 connect p_X000.p_X100.p_X120.p_X122.rp_370359531bcbeddd to p_X000.p_X100.p_X110.p_X112.rp_fc5798a77b6a020d {
            attribute connectionId : String = "CG-9A05AF4B79F0AC70EEBB8C27";
            attribute connectionType : String = "SIGNAL";
            attribute originalPath : String = "X122::PORT::X122::超级电容电压输出::ITM-MEA-025::输出 -> X112::PORT::X112::超级电容电压输入::ITM-MEA-025::输入";
        }
        interface c_CG_9ACDE46A41EE650430438B91 : IF_IF_CMD_016 connect p_N_4000.p_N_4200.p_N_4230.p_N_4238.rp_65aacc4600de3990 to p_N_8000.p_N_8100.p_N_8150.p_N_8151.rp_d7d7f4cb9554ff03 {
            attribute connectionId : String = "CG-9ACDE46A41EE650430438B91";
            attribute connectionType : String = "SIGNAL";
            attribute originalPath : String = "4238::PORT::4238::高压断路器指令输出::ITM-CMD-016::输出 -> 8151::PORT::8151::高压断路器指令输入::ITM-CMD-016::输入";
        }
        interface c_CG_9AE6E470A1C767E917CAED42 : IF_IF_CMD_030 connect p_N_8000.p_N_8100.p_N_8120.p_N_8127.rp_8f3091a86214dd4e to p_N_8000.p_N_8100.p_N_8120.p_N_8122.rp_ab848f3c1a74117a {
            attribute connectionId : String = "CG-9AE6E470A1C767E917CAED42";
            attribute connectionType : String = "SIGNAL";
            attribute originalPath : String = "8127::PORT::8127::安全停车_制动请求输出::ITM-CMD-030::输出 -> 8122::PORT::8122::安全停车_制动请求输入::ITM-CMD-030::输入";
        }
        interface c_CG_9B0510538F8E21B452D8C165 : IF_IF_STA_006 connect p_N_7000.p_N_7200.p_N_7210.p_N_7211.rp_43e35aa64c833efc to p_N_7000.p_N_7200.p_N_7280.p_N_7281.rp_5158f71b0a56da87 {
            attribute connectionId : String = "CG-9B0510538F8E21B452D8C165";
            attribute connectionType : String = "SIGNAL";
            attribute originalPath : String = "7211::PORT::7211::制动隔离状态输出::ITM-STA-006::输出 -> 7281::PORT::7281::制动隔离状态输入::ITM-STA-006::输入";
        }
        interface c_CG_9D3B4C2BDF604CDEBBA07160 : IF_IF_ACC_015 connect p_N_8000.p_N_8100.p_N_8160.p_N_8166.rp_0d75944292125dac to p_N_8000.p_N_8100.p_N_8120.p_N_8122.rp_b11b9e2ada11927e {
            attribute connectionId : String = "CG-9D3B4C2BDF604CDEBBA07160";
            attribute connectionType : String = "SIGNAL";
            attribute originalPath : String = "8166::PORT::8166::能量回收率输出::ITM-ACC-015::输出 -> 8122::PORT::8122::能量回收率输入::ITM-ACC-015::输入";
        }
        interface c_CG_9EB19436ED0A54ECCF52C717 : IF_IF_PHY_001 connect p_N_4000.p_N_4100.p_N_4110.p_N_4111.rp_ca65ceda639dfc7a to p_N_4000.p_N_4200.p_N_4210.p_N_4211.rp_bba7ece236be8f3c {
            attribute connectionId : String = "CG-9EB19436ED0A54ECCF52C717";
            attribute connectionType : String = "SERIES";
            attribute originalPath : String = "4111::PORT::4111::导流端高压交流电能端口::ITM-PHY-001::双向物理 -> 4211::PORT::4211::进线侧高压交流电能端口::ITM-PHY-001::双向物理";
        }
        interface c_CG_A0B82CF482DDFB4553F8CFCA : IF_IF_MEA_014 connect p_N_8000.p_N_8100.p_N_8120.p_N_8128.rp_8d19f6989a5bebad to p_N_7000.p_N_7200.p_N_7210.p_N_7211.rp_04cfaf63bfa3ed70 {
            attribute connectionId : String = "CG-A0B82CF482DDFB4553F8CFCA";
            attribute connectionType : String = "SIGNAL";
            attribute originalPath : String = "8128::PORT::8128::总风管压力输出::ITM-MEA-014::输出 -> 7211::PORT::7211::总风管压力输入::ITM-MEA-014::输入";
        }
        interface c_CG_A0E50849D53632A6F599B298 : IF_IF_CMD_025 connect p_X000.p_X100.p_X110.p_X112.rp_1ca011606f062f80 to p_X000.p_X100.p_X110.p_X111.rp_3ad794182f43f4d8 {
            attribute connectionId : String = "CG-A0E50849D53632A6F599B298";
            attribute connectionType : String = "SIGNAL";
            attribute originalPath : String = "X112::PORT::X112::储能功率请求输出::ITM-CMD-025::输出 -> X111::PORT::X111::储能功率请求输入::ITM-CMD-025::输入";
        }
        interface c_CG_A35E2178763C6233BE73AA36 : IF_IF_ACC_005 connect p_N_5000.p_N_5100.p_N_5140.p_N_5142.rp_ff09931c451e831b to p_N_8000.p_N_8100.p_N_8120.p_N_8122.rp_dae173a1561f3f35 {
            attribute connectionId : String = "CG-A35E2178763C6233BE73AA36";
            attribute connectionType : String = "SIGNAL";
            attribute originalPath : String = "5142::PORT::5142::制动电阻耗散功率输出::ITM-ACC-005::输出 -> 8122::PORT::8122::制动电阻耗散功率输入::ITM-ACC-005::输入";
        }
        interface c_CG_A3B31951ADAE62C498E76260 : IF_IF_CMD_001 connect p_D000.p_D100.p_D110.p_D112.rp_8962dea15ad904c6 to p_N_8000.p_N_8100.p_N_8120.p_N_8121.rp_2ee1cd48c6d41ac7 {
            attribute connectionId : String = "CG-A3B31951ADAE62C498E76260";
            attribute connectionType : String = "SIGNAL";
            attribute originalPath : String = "D112::PORT::D112::列车方向指令输出::ITM-CMD-001::输出 -> 8121::PORT::8121::列车方向指令输入::ITM-CMD-001::输入";
        }
        interface c_CG_A424455519797490E4F865AA : IF_IF_MEA_008 connect p_N_5000.p_N_5100.p_N_5140.p_N_5145.rp_1680714c67f7d311 to p_N_8000.p_N_8100.p_N_8160.p_N_8166.rp_54d624d57f57843b {
            attribute connectionId : String = "CG-A424455519797490E4F865AA";
            attribute connectionType : String = "SIGNAL";
            attribute originalPath : String = "5145::PORT::5145::中间直流母线电压输出::ITM-MEA-008::输出 -> 8166::PORT::8166::中间直流母线电压输入::ITM-MEA-008::输入";
        }
        interface c_CG_A467E486FE1FCC1FD2410729 : IF_IF_MEA_009 connect p_N_5000.p_N_5100.p_N_5140.p_N_5145.rp_a9cc4822e30a5ede to p_N_5000.p_N_5100.p_N_5110.p_N_5112.rp_6ad9df7ab3c91425 {
            attribute connectionId : String = "CG-A467E486FE1FCC1FD2410729";
            attribute connectionType : String = "SIGNAL";
            attribute originalPath : String = "5145::PORT::5145::中间直流母线电流输出::ITM-MEA-009::输出 -> 5112::PORT::5112::中间直流母线电流输入::ITM-MEA-009::输入";
        }
        interface c_CG_A6D783BBFCF6C6DA11FFCF2D : IF_IF_MEA_029 connect p_X000.p_X100.p_X110.p_X111.rp_9828766df3df1904 to p_N_8000.p_N_8100.p_N_8120.p_N_8122.rp_e1808e35289aaba6 {
            attribute connectionId : String = "CG-A6D783BBFCF6C6DA11FFCF2D";
            attribute connectionType : String = "SIGNAL";
            attribute originalPath : String = "X111::PORT::X111::双向DC_DC实际功率输出::ITM-MEA-029::输出 -> 8122::PORT::8122::双向DC_DC实际功率输入::ITM-MEA-029::输入";
        }
        interface c_CG_A7173AC81E21DD801A82E73D : IF_IF_STA_016 connect p_N_4000.p_N_4200.p_N_4230.p_N_4238.rp_9458944450b0dd4c to p_N_4000.p_N_4200.p_N_4230.p_N_4239.rp_be1480d12bc9092c {
            attribute connectionId : String = "CG-A7173AC81E21DD801A82E73D";
            attribute connectionType : String = "SIGNAL";
            attribute originalPath : String = "4238::PORT::4238::高压系统故障状态输出::ITM-STA-016::输出 -> 4239::PORT::4239::高压系统故障状态采集输入::ITM-STA-016::输入";
        }
        interface c_CG_A9A3297C8A71DEFC8975FC31 : IF_IF_PHY_013 connect p_X000.p_X100.p_X120.p_X124.rp_4d5eafc70549d9c0 to boundary_BOUNDARY_THERMAL_ENVIRONMENT.bp_2ac3a221090b246a {
            attribute connectionId : String = "CG-A9A3297C8A71DEFC8975FC31";
            attribute connectionType : String = "BOUNDARY";
            attribute originalPath : String = "X124::PORT::X124::超级电容热能感知端口::ITM-PHY-013::双向物理 -> BOUNDARY-THERMAL-ENVIRONMENT::BPORT::BOUNDARY-THERMAL-ENVIRONMENT::ITM-PHY-013";
        }
        interface c_CG_ACA2BC6B6BBEF201778733FC : IF_IF_STA_027 connect p_N_8000.p_N_8100.p_N_8120.p_N_8128.rp_58e3c9dfabb04a51 to p_N_8000.p_N_8100.p_N_8120.p_N_8121.rp_d5423b06aaccb6ac {
            attribute connectionId : String = "CG-ACA2BC6B6BBEF201778733FC";
            attribute connectionType : String = "SIGNAL";
            attribute originalPath : String = "8128::PORT::8128::ATP_外部安全系统状态输出::ITM-STA-027::输出 -> 8121::PORT::8121::ATP_外部安全系统状态输入::ITM-STA-027::输入";
        }
        interface c_CG_AF75A5003A9B1A8DE28924E1 : IF_IF_PHY_005 connect p_N_3000.p_N_3100.p_N_3120.p_N_3121.rp_6464b6253314b208 to p_N_3000.p_N_3100.p_N_3110.p_N_3112.rp_6917242b1f7fc50f {
            attribute connectionId : String = "CG-AF75A5003A9B1A8DE28924E1";
            attribute connectionType : String = "SERIES";
            attribute originalPath : String = "3121::PORT::3121::低速轴旋转机械能端口::ITM-PHY-005::双向物理 -> 3112::PORT::3112::传动段旋转机械能端口::ITM-PHY-005::双向物理";
        }
        interface c_CG_B1E191297C1D862473B2D371 : IF_IF_STA_001 connect p_N_8000.p_N_8100.p_N_8120.p_N_8125.rp_04f0621818e40445 to p_N_8000.p_N_8100.p_N_8120.p_N_8122.rp_b6a69bd683685d04 {
            attribute connectionId : String = "CG-B1E191297C1D862473B2D371";
            attribute connectionType : String = "SIGNAL";
            attribute originalPath : String = "8125::PORT::8125::牵引可用状态输出::ITM-STA-001::输出 -> 8122::PORT::8122::牵引可用状态输入::ITM-STA-001::输入";
        }
        interface c_CG_B251741505CB19FE47559F29 : IF_IF_CMD_006 connect p_N_7000.p_N_7200.p_N_7210.p_N_7211.rp_0194ebfed505dfb5 to p_N_8000.p_N_8100.p_N_8120.p_N_8125.rp_d69905c106b65d8f {
            attribute connectionId : String = "CG-B251741505CB19FE47559F29";
            attribute connectionType : String = "SIGNAL";
            attribute originalPath : String = "7211::PORT::7211::动态制动力请求输出::ITM-CMD-006::输出 -> 8125::PORT::8125::动态制动力请求输入::ITM-CMD-006::输入";
        }
        interface c_CG_B399D92EE15558C08A95FA03 : IF_IF_ACC_003 connect p_N_5000.p_N_5100.p_N_5130.p_N_5131.rp_95979f7c6bb276e7 to p_N_8000.p_N_8100.p_N_8120.p_N_8122.rp_eb1cf5594b5796be {
            attribute connectionId : String = "CG-B399D92EE15558C08A95FA03";
            attribute connectionType : String = "SIGNAL";
            attribute originalPath : String = "5131::PORT::5131::回馈电网功率输出::ITM-ACC-003::输出 -> 8122::PORT::8122::回馈电网功率输入::ITM-ACC-003::输入";
        }
        interface c_CG_B483D5C4E4EC5F805E3B0F19 : IF_IF_PHY_001 connect p_N_4000.p_N_4200.p_N_4230.p_N_4236.rp_78e99abb7d77c156 to p_N_4000.p_N_4500.p_N_4510.p_N_4511.rp_c782fb362436088e {
            attribute connectionId : String = "CG-B483D5C4E4EC5F805E3B0F19";
            attribute connectionType : String = "SERIES";
            attribute originalPath : String = "4236::PORT::4236::第二测量端高压交流电能端口::ITM-PHY-001::双向物理 -> 4511::PORT::4511::高压交流电能端口::ITM-PHY-001::双向物理";
        }
        interface c_CG_B5CE3B88204C1D03AD0527D2 : IF_IF_LIM_001 connect p_N_8000.p_N_8100.p_N_8120.p_N_8125.rp_b60dd66dcfd10afa to p_N_8000.p_N_8100.p_N_8120.p_N_8122.rp_e0814e233fa0db3e {
            attribute connectionId : String = "CG-B5CE3B88204C1D03AD0527D2";
            attribute connectionType : String = "SIGNAL";
            attribute originalPath : String = "8125::PORT::8125::可用动态制动力输出::ITM-LIM-001::输出 -> 8122::PORT::8122::可用动态制动力输入::ITM-LIM-001::输入";
        }
        interface c_CG_B99AB8690BDE418D1F8055E3 : IF_IF_CMD_010 connect p_N_5000.p_N_5100.p_N_5110.p_N_5111.rp_3c696476f82c2ae5 to p_N_5000.p_N_5100.p_N_5130.p_N_5131.rp_c06b535bf90fa905 {
            attribute connectionId : String = "CG-B99AB8690BDE418D1F8055E3";
            attribute connectionType : String = "SIGNAL";
            attribute originalPath : String = "5111::PORT::5111::网侧变流控制指令输出::ITM-CMD-010::输出 -> 5131::PORT::5131::网侧变流控制指令输入::ITM-CMD-010::输入";
        }
        interface c_CG_BB962E06FB56D8459F9A2BF0 : IF_IF_STA_001 connect p_N_8000.p_N_8100.p_N_8120.p_N_8125.rp_04f0621818e40445 to p_N_8000.p_N_8100.p_N_8120.p_N_8121.rp_37e2c2d63c55e098 {
            attribute connectionId : String = "CG-BB962E06FB56D8459F9A2BF0";
            attribute connectionType : String = "SIGNAL";
            attribute originalPath : String = "8125::PORT::8125::牵引可用状态输出::ITM-STA-001::输出 -> 8121::PORT::8121::牵引可用状态输入::ITM-STA-001::输入";
        }
        interface c_CG_BC53696D702792E563E6C045 : IF_IF_LIM_007 connect p_X000.p_X100.p_X110.p_X113.rp_d9c32040ebe6917e to p_X000.p_X100.p_X110.p_X112.rp_1f01277587ee6905 {
            attribute connectionId : String = "CG-BC53696D702792E563E6C045";
            attribute connectionType : String = "SIGNAL";
            attribute originalPath : String = "X113::PORT::X113::直流母线电压上限输出::ITM-LIM-007::输出 -> X112::PORT::X112::直流母线电压上限输入::ITM-LIM-007::输入";
        }
        interface c_CG_BDBC6DE36D711BE7257BA6A4 : IF_IF_PHY_013 connect p_N_5000.p_N_5100.p_N_5140.p_N_5142.rp_7c7ad9996d24b706 to boundary_BOUNDARY_THERMAL_ENVIRONMENT.bp_2ac3a221090b246a {
            attribute connectionId : String = "CG-BDBC6DE36D711BE7257BA6A4";
            attribute connectionType : String = "BOUNDARY";
            attribute originalPath : String = "5142::PORT::5142::热能_热流端口::ITM-PHY-013::双向物理 -> BOUNDARY-THERMAL-ENVIRONMENT::BPORT::BOUNDARY-THERMAL-ENVIRONMENT::ITM-PHY-013";
        }
        interface c_CG_BDD8747118488C9BE895D95F : IF_IF_LIM_005 connect p_N_5000.p_N_5100.p_N_5110.p_N_5111.rp_cd7720cf9a4eae22 to p_N_8000.p_N_8100.p_N_8120.p_N_8122.rp_abc36140248d0eef {
            attribute connectionId : String = "CG-BDD8747118488C9BE895D95F";
            attribute connectionType : String = "SIGNAL";
            attribute originalPath : String = "5111::PORT::5111::接触网可接收功率输出::ITM-LIM-005::输出 -> 8122::PORT::8122::接触网可接收功率输入::ITM-LIM-005::输入";
        }
        interface c_CG_BDE1416487389FCF7B495D3E : IF_IF_MEA_010 connect p_N_5000.p_N_5100.p_N_5110.p_N_5113.rp_4be030fa7e242206 to p_N_5000.p_N_5100.p_N_5110.p_N_5112.rp_3db204c2f5a83c7f {
            attribute connectionId : String = "CG-BDE1416487389FCF7B495D3E";
            attribute connectionType : String = "SIGNAL";
            attribute originalPath : String = "5113::PORT::5113::电机侧相电流输出::ITM-MEA-010::输出 -> 5112::PORT::5112::电机侧相电流输入::ITM-MEA-010::输入";
        }
        interface c_CG_BE9EAF0E7F50C277DA344138 : IF_IF_LIM_004 connect p_N_8000.p_N_8100.p_N_8120.p_N_8125.rp_91d8f479934c65da to p_N_8000.p_N_8100.p_N_8120.p_N_8122.rp_3aaf955421310ab3 {
            attribute connectionId : String = "CG-BE9EAF0E7F50C277DA344138";
            attribute connectionType : String = "SIGNAL";
            attribute originalPath : String = "8125::PORT::8125::再生功率上限输出::ITM-LIM-004::输出 -> 8122::PORT::8122::再生功率上限输入::ITM-LIM-004::输入";
        }
        interface c_CG_BEDE0932E86628B2EFCA8CCD : IF_IF_LIM_001 connect p_N_8000.p_N_8100.p_N_8120.p_N_8125.rp_b60dd66dcfd10afa to p_N_7000.p_N_7200.p_N_7210.p_N_7211.rp_e4d6047a07b1416e {
            attribute connectionId : String = "CG-BEDE0932E86628B2EFCA8CCD";
            attribute connectionType : String = "SIGNAL";
            attribute originalPath : String = "8125::PORT::8125::可用动态制动力输出::ITM-LIM-001::输出 -> 7211::PORT::7211::可用动态制动力输入::ITM-LIM-001::输入";
        }
        interface c_CG_BF14D9A0947A4893C7260661 : IF_IF_PHY_001 connect p_N_4000.p_N_4200.p_N_4210.p_N_4212.rp_e1689d643b97d378 to p_N_4000.p_N_4200.p_N_4230.p_N_4236.rp_bb6f3fee449fd865 {
            attribute connectionId : String = "CG-BF14D9A0947A4893C7260661";
            attribute connectionType : String = "SERIES";
            attribute originalPath : String = "4212::PORT::4212::出线侧高压交流电能端口::ITM-PHY-001::双向物理 -> 4236::PORT::4236::第一测量端高压交流电能端口::ITM-PHY-001::双向物理";
        }
        interface c_CG_C003C81FB79009EC9E0DAC6B : IF_IF_CMD_028 connect p_X000.p_X100.p_X110.p_X112.rp_adb78cdbb75469df to p_X000.p_X100.p_X130.p_X132.rp_4d68d3f9ee4e0009 {
            attribute connectionId : String = "CG-C003C81FB79009EC9E0DAC6B";
            attribute connectionType : String = "SIGNAL";
            attribute originalPath : String = "X112::PORT::X112::储能预充电指令输出::ITM-CMD-028::输出 -> X132::PORT::X132::储能预充电指令输入::ITM-CMD-028::输入";
        }
        interface c_CG_C03EBDD9B3CFF4E6611E41A1 : IF_IF_STA_030 connect p_X000.p_X100.p_X110.p_X112.rp_3b946767139d884a to p_N_8000.p_N_8100.p_N_8120.p_N_8122.rp_1967a947dd39d4a5 {
            attribute connectionId : String = "CG-C03EBDD9B3CFF4E6611E41A1";
            attribute connectionType : String = "SIGNAL";
            attribute originalPath : String = "X112::PORT::X112::储能系统可用状态输出::ITM-STA-030::输出 -> 8122::PORT::8122::储能系统可用状态输入::ITM-STA-030::输入";
        }
        interface c_CG_C0F5EB5317440FA36F0491AE : IF_IF_STA_024 connect p_N_8000.p_N_8100.p_N_8120.p_N_8128.rp_cb74be2d7d4a54c7 to p_N_8000.p_N_8100.p_N_8120.p_N_8121.rp_2455eff74badb007 {
            attribute connectionId : String = "CG-C0F5EB5317440FA36F0491AE";
            attribute connectionType : String = "SIGNAL";
            attribute originalPath : String = "8128::PORT::8128::高压安全回路状态输出::ITM-STA-024::输出 -> 8121::PORT::8121::高压安全回路状态输入::ITM-STA-024::输入";
        }
        interface c_CG_C113ED5B462ACDD4ACE56E91 : IF_IF_STA_031 connect p_X000.p_X100.p_X110.p_X112.rp_e5eadfefaf46ac0a to p_N_8000.p_N_8100.p_N_8120.p_N_8122.rp_9d3500c169fe7103 {
            attribute connectionId : String = "CG-C113ED5B462ACDD4ACE56E91";
            attribute connectionType : String = "SIGNAL";
            attribute originalPath : String = "X112::PORT::X112::储能系统故障状态输出::ITM-STA-031::输出 -> 8122::PORT::8122::储能系统故障状态输入::ITM-STA-031::输入";
        }
        interface c_CG_C2F8D7B23A3941D29EE9543F : IF_IF_MEA_029 connect p_X000.p_X100.p_X110.p_X111.rp_9828766df3df1904 to p_X000.p_X100.p_X110.p_X112.rp_4659cbe7e3b50b58 {
            attribute connectionId : String = "CG-C2F8D7B23A3941D29EE9543F";
            attribute connectionType : String = "SIGNAL";
            attribute originalPath : String = "X111::PORT::X111::双向DC_DC实际功率输出::ITM-MEA-029::输出 -> X112::PORT::X112::双向DC_DC实际功率输入::ITM-MEA-029::输入";
        }
        interface c_CG_C346B9ABBAE556A332DA422F : IF_IF_MEA_006 connect p_N_4000.p_N_4200.p_N_4230.p_N_4236.rp_9107465175683792 to p_N_4000.p_N_4200.p_N_4230.p_N_4238.rp_afb7b0997d28e7cb {
            attribute connectionId : String = "CG-C346B9ABBAE556A332DA422F";
            attribute connectionType : String = "SIGNAL";
            attribute originalPath : String = "4236::PORT::4236::高压线路电流输出::ITM-MEA-006::输出 -> 4238::PORT::4238::高压线路电流输入::ITM-MEA-006::输入";
        }
        interface c_CG_C3FD4BDC3D0E9ABF609DAE81 : IF_IF_CMD_018 connect p_N_4000.p_N_4200.p_N_4230.p_N_4239.rp_327ede77d6565c4b to p_N_4000.p_N_4200.p_N_4230.p_N_4238.rp_71811e4b68798212 {
            attribute connectionId : String = "CG-C3FD4BDC3D0E9ABF609DAE81";
            attribute connectionType : String = "SIGNAL";
            attribute originalPath : String = "4239::PORT::4239::受电弓控制指令输出::ITM-CMD-018::输出 -> 4238::PORT::4238::受电弓控制指令输入::ITM-CMD-018::输入";
        }
        interface c_CG_C53D41B4A1F64D70B4607AA4 : IF_IF_PHY_006 connect p_N_3000.p_N_3100.p_N_3110.p_N_3111.rp_8ee7c79c0fe26b93 to boundary_BOUNDARY_RAIL.bp_cf72f055f5b12b85 {
            attribute connectionId : String = "CG-C53D41B4A1F64D70B4607AA4";
            attribute connectionType : String = "BOUNDARY";
            attribute originalPath : String = "3111::PORT::3111::轮轨纵向机械作用端口::ITM-PHY-006::双向物理 -> BOUNDARY-RAIL::BPORT::BOUNDARY-RAIL::ITM-PHY-006";
        }
        interface c_CG_C5E43804F4CA212D668FD997 : IF_IF_STA_032 connect p_X000.p_X100.p_X130.p_X131.rp_c029b3b1472e957d to p_X000.p_X100.p_X110.p_X112.rp_f929a9fa6b633837 {
            attribute connectionId : String = "CG-C5E43804F4CA212D668FD997";
            attribute connectionType : String = "SIGNAL";
            attribute originalPath : String = "X131::PORT::X131::储能主接触器状态输出::ITM-STA-032::输出 -> X112::PORT::X112::储能主接触器状态输入::ITM-STA-032::输入";
        }
        interface c_CG_C64E0682EDDBDDD748BA13CA : IF_IF_STA_013 connect p_N_4000.p_N_4200.p_N_4230.p_N_4238.rp_0674d2b80a6a72da to p_N_4000.p_N_4200.p_N_4230.p_N_4239.rp_1fd23591362c1d8d {
            attribute connectionId : String = "CG-C64E0682EDDBDDD748BA13CA";
            attribute connectionType : String = "SIGNAL";
            attribute originalPath : String = "4238::PORT::4238::高压断路器状态输出::ITM-STA-013::输出 -> 4239::PORT::4239::高压断路器状态输入::ITM-STA-013::输入";
        }
        interface c_CG_C6A9FBA7CCD28311320F3552 : IF_IF_CMD_030 connect p_N_8000.p_N_8100.p_N_8120.p_N_8127.rp_8f3091a86214dd4e to p_N_8000.p_N_8100.p_N_8120.p_N_8121.rp_4325db72e2d88769 {
            attribute connectionId : String = "CG-C6A9FBA7CCD28311320F3552";
            attribute connectionType : String = "SIGNAL";
            attribute originalPath : String = "8127::PORT::8127::安全停车_制动请求输出::ITM-CMD-030::输出 -> 8121::PORT::8121::安全停车_制动请求输入::ITM-CMD-030::输入";
        }
        interface c_CG_C7C6703197747322B57096B5 : IF_IF_MEA_017 connect p_N_7000.p_N_7200.p_N_7250.p_N_7252.rp_6e046e892954d0de to p_N_7000.p_N_7200.p_N_7210.p_N_7211.rp_5b7be52aa5b6e9d0 {
            attribute connectionId : String = "CG-C7C6703197747322B57096B5";
            attribute connectionType : String = "SIGNAL";
            attribute originalPath : String = "7252::PORT::7252::实际摩擦制动力输出::ITM-MEA-017::输出 -> 7211::PORT::7211::实际摩擦制动力输入::ITM-MEA-017::输入";
        }
        interface c_CG_C81A2253CDA9FC6173740074 : IF_IF_PHY_005 connect p_N_3000.p_N_3100.p_N_3110.p_N_3112.rp_c530418a51140052 to p_N_3000.p_N_3100.p_N_3110.p_N_3111.rp_f0350fc816a551ff {
            attribute connectionId : String = "CG-C81A2253CDA9FC6173740074";
            attribute connectionType : String = "SERIES";
            attribute originalPath : String = "3112::PORT::3112::轮对段旋转机械能端口::ITM-PHY-005::双向物理 -> 3111::PORT::3111::轮轴旋转机械能端口::ITM-PHY-005::双向物理";
        }
        interface c_CG_C8FE042475056BF85CFA2B40 : IF_IF_MEA_008 connect p_N_5000.p_N_5100.p_N_5140.p_N_5145.rp_1680714c67f7d311 to p_N_8000.p_N_8100.p_N_8120.p_N_8125.rp_7262595caaf3b8d8 {
            attribute connectionId : String = "CG-C8FE042475056BF85CFA2B40";
            attribute connectionType : String = "SIGNAL";
            attribute originalPath : String = "5145::PORT::5145::中间直流母线电压输出::ITM-MEA-008::输出 -> 8125::PORT::8125::中间直流母线电压输入::ITM-MEA-008::输入";
        }
        interface c_CG_C9CA06B236DB453EEFEC07E6 : IF_IF_STA_013 connect p_N_4000.p_N_4200.p_N_4210.p_N_4211.rp_5301bf8bda8fba16 to p_N_4000.p_N_4200.p_N_4230.p_N_4238.rp_b26de8005dff4962 {
            attribute connectionId : String = "CG-C9CA06B236DB453EEFEC07E6";
            attribute connectionType : String = "SIGNAL";
            attribute originalPath : String = "4211::PORT::4211::高压断路器状态输出::ITM-STA-013::输出 -> 4238::PORT::4238::高压断路器状态输入::ITM-STA-013::输入";
        }
        interface c_CG_CB302083C9F33A1345D9C406 : IF_IF_LIM_009 connect p_X000.p_X100.p_X110.p_X112.rp_388d943a537916a7 to p_N_8000.p_N_8100.p_N_8120.p_N_8122.rp_8c3ed075d33335e8 {
            attribute connectionId : String = "CG-CB302083C9F33A1345D9C406";
            attribute connectionType : String = "SIGNAL";
            attribute originalPath : String = "X112::PORT::X112::储能可用充电功率输出::ITM-LIM-009::输出 -> 8122::PORT::8122::储能可用充电功率输入::ITM-LIM-009::输入";
        }
        interface c_CG_CCE3D228C7F2AEE6207C1B6A : IF_IF_CMD_020 connect p_N_7000.p_N_7200.p_N_7210.p_N_7211.rp_a882b33038ce4623 to p_N_7000.p_N_7200.p_N_7280.p_N_7284.rp_0b1d53051662d3f2 {
            attribute connectionId : String = "CG-CCE3D228C7F2AEE6207C1B6A";
            attribute connectionType : String = "SIGNAL";
            attribute originalPath : String = "7211::PORT::7211::制动隔离指令输出::ITM-CMD-020::输出 -> 7284::PORT::7284::制动隔离指令输入::ITM-CMD-020::输入";
        }
        interface c_CG_CD05C34D37DBECA08731CAFA : IF_IF_MEA_006 connect p_N_4000.p_N_4200.p_N_4230.p_N_4238.rp_c7dcc306b020116f to p_N_4000.p_N_4200.p_N_4230.p_N_4239.rp_1a7ff383166e59f0 {
            attribute connectionId : String = "CG-CD05C34D37DBECA08731CAFA";
            attribute connectionType : String = "SIGNAL";
            attribute originalPath : String = "4238::PORT::4238::高压线路电流输出::ITM-MEA-006::输出 -> 4239::PORT::4239::高压线路电流输入::ITM-MEA-006::输入";
        }
        interface c_CG_CE151D40A2BF816F41762F4C : IF_IF_STA_025 connect p_N_8000.p_N_8100.p_N_8150.p_N_8152.rp_ae53feffb1e116e3 to p_N_7000.p_N_7200.p_N_7210.p_N_7211.rp_daaf414c1711f2bd {
            attribute connectionId : String = "CG-CE151D40A2BF816F41762F4C";
            attribute connectionType : String = "SIGNAL";
            attribute originalPath : String = "8152::PORT::8152::制动安全回路状态输出::ITM-STA-025::输出 -> 7211::PORT::7211::制动安全回路状态输入::ITM-STA-025::输入";
        }
        interface c_CG_CE2820923CC0CB141833E11D : IF_IF_STA_016 connect p_N_4000.p_N_4200.p_N_4230.p_N_4238.rp_9458944450b0dd4c to p_N_4000.p_N_4500.p_N_4510.p_N_4518.rp_a87c9390595138d6 {
            attribute connectionId : String = "CG-CE2820923CC0CB141833E11D";
            attribute connectionType : String = "SIGNAL";
            attribute originalPath : String = "4238::PORT::4238::高压系统故障状态输出::ITM-STA-016::输出 -> 4518::PORT::4518::高压系统故障状态输入::ITM-STA-016::输入";
        }
        interface c_CG_D1D66AE9099CD7FA32C270A6 : IF_IF_CMD_021 connect p_N_7000.p_N_7200.p_N_7210.p_N_7211.rp_dff51f26bbd38512 to p_N_7000.p_N_7200.p_N_7220.p_N_7222.rp_ddeea781987ee55c {
            attribute connectionId : String = "CG-D1D66AE9099CD7FA32C270A6";
            attribute connectionType : String = "SIGNAL";
            attribute originalPath : String = "7211::PORT::7211::电空转换阀指令输出::ITM-CMD-021::输出 -> 7222::PORT::7222::电空转换阀指令输入::ITM-CMD-021::输入";
        }
        interface c_CG_D2E26B7066F1A62115B06D59 : IF_IF_STA_014 connect p_N_4000.p_N_4200.p_N_4230.p_N_4238.rp_7fe2b8fd826583f2 to p_N_4000.p_N_4200.p_N_4230.p_N_4239.rp_30bf7d79603b941d {
            attribute connectionId : String = "CG-D2E26B7066F1A62115B06D59";
            attribute connectionType : String = "SIGNAL";
            attribute originalPath : String = "4238::PORT::4238::高压隔离开关状态输出::ITM-STA-014::输出 -> 4239::PORT::4239::高压隔离开关状态输入::ITM-STA-014::输入";
        }
        interface c_CG_D338FAEF97B977B2FE95051B : IF_IF_MEA_008 connect p_N_5000.p_N_5100.p_N_5140.p_N_5145.rp_1680714c67f7d311 to p_N_5000.p_N_5100.p_N_5110.p_N_5112.rp_69252f780afe77e0 {
            attribute connectionId : String = "CG-D338FAEF97B977B2FE95051B";
            attribute connectionType : String = "SIGNAL";
            attribute originalPath : String = "5145::PORT::5145::中间直流母线电压输出::ITM-MEA-008::输出 -> 5112::PORT::5112::中间直流母线电压输入::ITM-MEA-008::输入";
        }
        interface c_CG_D44FA955851A05FB81FD0837 : IF_IF_MEA_005 connect p_N_4000.p_N_4200.p_N_4230.p_N_4238.rp_5576b5e0dbb912ba to p_N_4000.p_N_4200.p_N_4240.p_N_4241.rp_2b7dd272027fdc0b {
            attribute connectionId : String = "CG-D44FA955851A05FB81FD0837";
            attribute connectionType : String = "SIGNAL";
            attribute originalPath : String = "4238::PORT::4238::高压线路电压输出::ITM-MEA-005::输出 -> 4241::PORT::4241::高压线路电压输入::ITM-MEA-005::输入";
        }
        interface c_CG_D4DF5719633CB5B375F35094 : IF_IF_MEA_012 connect p_N_5000.p_N_5300.p_N_5310.p_N_5311.rp_10bb4c4f0063bc18 to p_N_5000.p_N_5100.p_N_5110.p_N_5112.rp_4557e9b0656c46f5 {
            attribute connectionId : String = "CG-D4DF5719633CB5B375F35094";
            attribute connectionType : String = "SIGNAL";
            attribute originalPath : String = "5311::PORT::5311::牵引电机实际转矩输出::ITM-MEA-012::输出 -> 5112::PORT::5112::牵引电机实际转矩输入::ITM-MEA-012::输入";
        }
        interface c_CG_D8FCE908D4FD9343C6353985 : IF_IF_CMD_029 connect p_N_8000.p_N_8100.p_N_8120.p_N_8122.rp_47c78247980cc3a5 to p_X000.p_X100.p_X110.p_X112.rp_b84f02a624b9982f {
            attribute connectionId : String = "CG-D8FCE908D4FD9343C6353985";
            attribute connectionType : String = "SIGNAL";
            attribute originalPath : String = "8122::PORT::8122::储能故障复位指令输出::ITM-CMD-029::输出 -> X112::PORT::X112::储能故障复位指令输入::ITM-CMD-029::输入";
        }
        interface c_CG_D9445FD2D7B8285174B3AE22 : IF_IF_MEA_030 connect p_X000.p_X100.p_X110.p_X113.rp_30a4f2a71d158c56 to p_X000.p_X100.p_X110.p_X112.rp_88bb7293920adfa8 {
            attribute connectionId : String = "CG-D9445FD2D7B8285174B3AE22";
            attribute connectionType : String = "SIGNAL";
            attribute originalPath : String = "X113::PORT::X113::双向DC_DC电流输出::ITM-MEA-030::输出 -> X112::PORT::X112::双向DC_DC电流输入::ITM-MEA-030::输入";
        }
        interface c_CG_D9940860A6DB9E6BD5200881 : IF_IF_PHY_013 connect p_N_3000.p_N_3100.p_N_3130.p_N_3131.rp_ec78c2de89f1a17c to boundary_BOUNDARY_THERMAL_ENVIRONMENT.bp_2ac3a221090b246a {
            attribute connectionId : String = "CG-D9940860A6DB9E6BD5200881";
            attribute connectionType : String = "BOUNDARY";
            attribute originalPath : String = "3131::PORT::3131::热能_热流端口::ITM-PHY-013::双向物理 -> BOUNDARY-THERMAL-ENVIRONMENT::BPORT::BOUNDARY-THERMAL-ENVIRONMENT::ITM-PHY-013";
        }
        interface c_CG_D9CD1E8933F596F319A67625 : IF_IF_CMD_028 connect p_N_8000.p_N_8100.p_N_8120.p_N_8122.rp_f704c2e7bab06749 to p_X000.p_X100.p_X110.p_X112.rp_5ff890136d5d49bf {
            attribute connectionId : String = "CG-D9CD1E8933F596F319A67625";
            attribute connectionType : String = "SIGNAL";
            attribute originalPath : String = "8122::PORT::8122::储能预充电指令输出::ITM-CMD-028::输出 -> X112::PORT::X112::储能预充电指令输入::ITM-CMD-028::输入";
        }
        interface c_CG_DA869E241F8A36DBAAC07E48 : IF_IF_PHY_007 connect p_N_7000.p_N_7200.p_N_7250.p_N_7254.rp_d9511ef0fa1c17df to p_N_3000.p_N_3100.p_N_3130.p_N_3131.rp_06d152ddc255f2eb {
            attribute connectionId : String = "CG-DA869E241F8A36DBAAC07E48";
            attribute connectionType : String = "SERIES";
            attribute originalPath : String = "7254::PORT::7254::摩擦制动机械作用端口::ITM-PHY-007::双向物理 -> 3131::PORT::3131::摩擦制动机械作用端口::ITM-PHY-007::双向物理";
        }
        interface c_CG_DAF7D43DDD825831F29A70F8 : IF_IF_LIM_010 connect p_X000.p_X100.p_X110.p_X112.rp_73067cce4e6a7eeb to p_N_8000.p_N_8100.p_N_8120.p_N_8122.rp_35b0ef67b409e840 {
            attribute connectionId : String = "CG-DAF7D43DDD825831F29A70F8";
            attribute connectionType : String = "SIGNAL";
            attribute originalPath : String = "X112::PORT::X112::储能可用放电功率输出::ITM-LIM-010::输出 -> 8122::PORT::8122::储能可用放电功率输入::ITM-LIM-010::输入";
        }
        interface c_CG_E0DB6C9771E2E272BC041D82 : IF_IF_CMD_016 connect p_N_4000.p_N_4200.p_N_4230.p_N_4238.rp_65aacc4600de3990 to p_N_4000.p_N_4200.p_N_4210.p_N_4211.rp_17bc6a2a377dffab {
            attribute connectionId : String = "CG-E0DB6C9771E2E272BC041D82";
            attribute connectionType : String = "SIGNAL";
            attribute originalPath : String = "4238::PORT::4238::高压断路器指令输出::ITM-CMD-016::输出 -> 4211::PORT::4211::高压断路器指令输入::ITM-CMD-016::输入";
        }
        interface c_CG_E5A3740D9F06BF31CB55A481 : IF_IF_PHY_012 connect p_N_3000.p_N_3800.p_N_3810.p_N_3813.rp_c843e562c7ec3ed9 to p_N_3000.p_N_3800.p_N_3810.p_N_3814.rp_43d42f25a744fe07 {
            attribute connectionId : String = "CG-E5A3740D9F06BF31CB55A481";
            attribute connectionType : String = "SERIES";
            attribute originalPath : String = "3813::PORT::3813::砂流端口::ITM-PHY-012::双向物理 -> 3814::PORT::3814::砂流端口::ITM-PHY-012::双向物理";
        }
        interface c_CG_E85E42C2A83EE58624438A26 : IF_IF_MEA_009 connect p_N_5000.p_N_5100.p_N_5140.p_N_5145.rp_a9cc4822e30a5ede to p_N_5000.p_N_5100.p_N_5110.p_N_5111.rp_0e00d1e837346b81 {
            attribute connectionId : String = "CG-E85E42C2A83EE58624438A26";
            attribute connectionType : String = "SIGNAL";
            attribute originalPath : String = "5145::PORT::5145::中间直流母线电流输出::ITM-MEA-009::输出 -> 5111::PORT::5111::中间直流母线电流输入::ITM-MEA-009::输入";
        }
        interface c_CG_E8DAA56D71F2BE4B5E1C9BBF : IF_IF_MEA_013 connect p_N_8000.p_N_8100.p_N_8120.p_N_8125.rp_36a59f5828d4c515 to p_N_7000.p_N_7200.p_N_7210.p_N_7211.rp_179bcc3fb8dacbbf {
            attribute connectionId : String = "CG-E8DAA56D71F2BE4B5E1C9BBF";
            attribute connectionType : String = "SIGNAL";
            attribute originalPath : String = "8125::PORT::8125::实际动态制动力输出::ITM-MEA-013::输出 -> 7211::PORT::7211::实际动态制动力输入::ITM-MEA-013::输入";
        }
        interface c_CG_E9224B53F74EDFCCFDA0FC70 : IF_IF_MEA_016 connect p_N_7000.p_N_7200.p_N_7220.p_N_722B.rp_8d219d5375ded80b to p_N_8000.p_N_8100.p_N_8120.p_N_8128.rp_cc7a917501039195 {
            attribute connectionId : String = "CG-E9224B53F74EDFCCFDA0FC70";
            attribute connectionType : String = "SIGNAL";
            attribute originalPath : String = "722B::PORT::722B::制动缸压力输出::ITM-MEA-016::输出 -> 8128::PORT::8128::制动缸压力输入::ITM-MEA-016::输入";
        }
        interface c_CG_E9AAF8010953F56E28D65ACF : IF_IF_CMD_031 connect p_N_7000.p_N_7200.p_N_7210.p_N_7211.rp_0209c7a801f78e7e to p_N_7000.p_N_7200.p_N_7210.p_N_7213.rp_de845d22bfa40612 {
            attribute connectionId : String = "CG-E9AAF8010953F56E28D65ACF";
            attribute connectionType : String = "SIGNAL";
            attribute originalPath : String = "7211::PORT::7211::制动控制接触器指令输出::ITM-CMD-031::输出 -> 7213::PORT::7213::制动控制接触器指令输入::ITM-CMD-031::输入";
        }
        interface c_CG_ED49C68C1459BB1005D412BB : IF_IF_CMD_030 connect p_N_8000.p_N_8100.p_N_8120.p_N_8127.rp_8f3091a86214dd4e to p_N_7000.p_N_7200.p_N_7210.p_N_7211.rp_da3049ae66223d22 {
            attribute connectionId : String = "CG-ED49C68C1459BB1005D412BB";
            attribute connectionType : String = "SIGNAL";
            attribute originalPath : String = "8127::PORT::8127::安全停车_制动请求输出::ITM-CMD-030::输出 -> 7211::PORT::7211::安全停车_制动请求输入::ITM-CMD-030::输入";
        }
        interface c_CG_F55B5E17D8CBFAC80E0961C2 : IF_IF_STA_024 connect p_N_8000.p_N_8100.p_N_8120.p_N_8128.rp_cb74be2d7d4a54c7 to p_N_4000.p_N_4200.p_N_4230.p_N_4239.rp_c9c4c887a8c7b2f0 {
            attribute connectionId : String = "CG-F55B5E17D8CBFAC80E0961C2";
            attribute connectionType : String = "SIGNAL";
            attribute originalPath : String = "8128::PORT::8128::高压安全回路状态输出::ITM-STA-024::输出 -> 4239::PORT::4239::高压安全回路状态输入::ITM-STA-024::输入";
        }
        interface c_CG_F69B9F4B8E034908EE3FE467 : IF_IF_PHY_013 connect p_N_7000.p_N_7200.p_N_7250.p_N_7254.rp_a60f1e83b03ea6d4 to boundary_BOUNDARY_THERMAL_ENVIRONMENT.bp_2ac3a221090b246a {
            attribute connectionId : String = "CG-F69B9F4B8E034908EE3FE467";
            attribute connectionType : String = "BOUNDARY";
            attribute originalPath : String = "7254::PORT::7254::热能_热流端口::ITM-PHY-013::双向物理 -> BOUNDARY-THERMAL-ENVIRONMENT::BPORT::BOUNDARY-THERMAL-ENVIRONMENT::ITM-PHY-013";
        }
        interface c_CG_F85BCC7C68AD281053865693 : IF_IF_CMD_016 connect p_N_4000.p_N_4200.p_N_4230.p_N_4239.rp_e67f315619e85b76 to p_N_4000.p_N_4200.p_N_4230.p_N_4238.rp_d6b968957e3167c7 {
            attribute connectionId : String = "CG-F85BCC7C68AD281053865693";
            attribute connectionType : String = "SIGNAL";
            attribute originalPath : String = "4239::PORT::4239::高压断路器指令输出::ITM-CMD-016::输出 -> 4238::PORT::4238::高压断路器指令输入::ITM-CMD-016::输入";
        }
        interface c_CG_FA31DFA220FEF0D6FAC8EB67 : IF_IF_PHY_005 connect p_N_3000.p_N_3600.p_N_3640.p_N_3641.rp_4ddc6037e5eea6fc to p_N_3000.p_N_3100.p_N_3110.p_N_3112.rp_c530418a51140052 {
            attribute connectionId : String = "CG-FA31DFA220FEF0D6FAC8EB67";
            attribute connectionType : String = "TAP";
            attribute originalPath : String = "3641::PORT::3641::旋转机械能端口::ITM-PHY-005::双向物理 -> 3112::PORT::3112::轮对段旋转机械能端口::ITM-PHY-005::双向物理";
        }
        interface c_CG_FD763799DECBFD4A6F4F94AD : IF_IF_CMD_020 connect p_N_7000.p_N_7200.p_N_7210.p_N_7211.rp_a882b33038ce4623 to p_N_7000.p_N_7200.p_N_7220.p_N_7228.rp_8b8dde76f47ec820 {
            attribute connectionId : String = "CG-FD763799DECBFD4A6F4F94AD";
            attribute connectionType : String = "SIGNAL";
            attribute originalPath : String = "7211::PORT::7211::制动隔离指令输出::ITM-CMD-020::输出 -> 7228::PORT::7228::制动隔离指令输入::ITM-CMD-020::输入";
        }
        interface c_CG_FE573ED935CFF37491A053E8 : IF_IF_MEA_006 connect p_N_4000.p_N_4200.p_N_4230.p_N_4238.rp_c7dcc306b020116f to p_N_8000.p_N_8100.p_N_8160.p_N_8166.rp_d9d89be1583c0e18 {
            attribute connectionId : String = "CG-FE573ED935CFF37491A053E8";
            attribute connectionType : String = "SIGNAL";
            attribute originalPath : String = "4238::PORT::4238::高压线路电流输出::ITM-MEA-006::输出 -> 8166::PORT::8166::高压线路电流输入::ITM-MEA-006::输入";
        }
    }
}

package FunctionAllocations {
    private import FunctionDefinitions::*;
    private import ProductDefinitions::*;
    action fu_F_3000_01 : FN_F_3000_01;
    action fu_F_3100_01 : FN_F_3100_01;
    action fu_F_3110_01 : FN_F_3110_01;
    action fu_F_3111_01 : FN_F_3111_01;
    action fu_F_3112_01 : FN_F_3112_01;
    action fu_F_3120_01 : FN_F_3120_01;
    action fu_F_3121_01 : FN_F_3121_01;
    action fu_F_3130_01 : FN_F_3130_01;
    action fu_F_3131_01 : FN_F_3131_01;
    action fu_F_3132_01 : FN_F_3132_01;
    action fu_F_3133_01 : FN_F_3133_01;
    action fu_F_3500_01 : FN_F_3500_01;
    action fu_F_3510_01 : FN_F_3510_01;
    action fu_F_3511_01 : FN_F_3511_01;
    action fu_F_3512_01 : FN_F_3512_01;
    action fu_F_3514_01 : FN_F_3514_01;
    action fu_F_3600_01 : FN_F_3600_01;
    action fu_F_3640_01 : FN_F_3640_01;
    action fu_F_3641_01 : FN_F_3641_01;
    action fu_F_3643_01 : FN_F_3643_01;
    action fu_F_3644_01 : FN_F_3644_01;
    action fu_F_3800_01 : FN_F_3800_01;
    action fu_F_3810_01 : FN_F_3810_01;
    action fu_F_3811_01 : FN_F_3811_01;
    action fu_F_3811_02 : FN_F_3811_02;
    action fu_F_3813_01 : FN_F_3813_01;
    action fu_F_3814_01 : FN_F_3814_01;
    action fu_F_4000_01 : FN_F_4000_01;
    action fu_F_4100_01 : FN_F_4100_01;
    action fu_F_4110_01 : FN_F_4110_01;
    action fu_F_4111_01 : FN_F_4111_01;
    action fu_F_411C_01 : FN_F_411C_01;
    action fu_F_411C_02 : FN_F_411C_02;
    action fu_F_4200_01 : FN_F_4200_01;
    action fu_F_4210_01 : FN_F_4210_01;
    action fu_F_4211_01 : FN_F_4211_01;
    action fu_F_4212_01 : FN_F_4212_01;
    action fu_F_4230_01 : FN_F_4230_01;
    action fu_F_4235_01 : FN_F_4235_01;
    action fu_F_4236_01 : FN_F_4236_01;
    action fu_F_4238_01 : FN_F_4238_01;
    action fu_F_4238_02 : FN_F_4238_02;
    action fu_F_4238_03 : FN_F_4238_03;
    action fu_F_4239_01 : FN_F_4239_01;
    action fu_F_4239_02 : FN_F_4239_02;
    action fu_F_4239_03 : FN_F_4239_03;
    action fu_F_4240_01 : FN_F_4240_01;
    action fu_F_4241_01 : FN_F_4241_01;
    action fu_F_4241_02 : FN_F_4241_02;
    action fu_F_4241_03 : FN_F_4241_03;
    action fu_F_4400_01 : FN_F_4400_01;
    action fu_F_4410_01 : FN_F_4410_01;
    action fu_F_4411_01 : FN_F_4411_01;
    action fu_F_4412_01 : FN_F_4412_01;
    action fu_F_4413_01 : FN_F_4413_01;
    action fu_F_4500_01 : FN_F_4500_01;
    action fu_F_4510_01 : FN_F_4510_01;
    action fu_F_4511_01 : FN_F_4511_01;
    action fu_F_4513_01 : FN_F_4513_01;
    action fu_F_4517_01 : FN_F_4517_01;
    action fu_F_4518_01 : FN_F_4518_01;
    action fu_F_4518_02 : FN_F_4518_02;
    action fu_F_5000_01 : FN_F_5000_01;
    action fu_F_5100_01 : FN_F_5100_01;
    action fu_F_5110_01 : FN_F_5110_01;
    action fu_F_5111_01 : FN_F_5111_01;
    action fu_F_5111_02 : FN_F_5111_02;
    action fu_F_5111_03 : FN_F_5111_03;
    action fu_F_5111_04 : FN_F_5111_04;
    action fu_F_5112_01 : FN_F_5112_01;
    action fu_F_5112_02 : FN_F_5112_02;
    action fu_F_5112_03 : FN_F_5112_03;
    action fu_F_5112_04 : FN_F_5112_04;
    action fu_F_5113_01 : FN_F_5113_01;
    action fu_F_5120_01 : FN_F_5120_01;
    action fu_F_5121_01 : FN_F_5121_01;
    action fu_F_5122_01 : FN_F_5122_01;
    action fu_F_5130_01 : FN_F_5130_01;
    action fu_F_5131_01 : FN_F_5131_01;
    action fu_F_5131_02 : FN_F_5131_02;
    action fu_F_5132_01 : FN_F_5132_01;
    action fu_F_5132_02 : FN_F_5132_02;
    action fu_F_5133_01 : FN_F_5133_01;
    action fu_F_5133_02 : FN_F_5133_02;
    action fu_F_5133_03 : FN_F_5133_03;
    action fu_F_5140_01 : FN_F_5140_01;
    action fu_F_5142_01 : FN_F_5142_01;
    action fu_F_5142_02 : FN_F_5142_02;
    action fu_F_5145_01 : FN_F_5145_01;
    action fu_F_5300_01 : FN_F_5300_01;
    action fu_F_5310_01 : FN_F_5310_01;
    action fu_F_5311_01 : FN_F_5311_01;
    action fu_F_5311_02 : FN_F_5311_02;
    action fu_F_7000_01 : FN_F_7000_01;
    action fu_F_7100_01 : FN_F_7100_01;
    action fu_F_7120_01 : FN_F_7120_01;
    action fu_F_7124_01 : FN_F_7124_01;
    action fu_F_7130_01 : FN_F_7130_01;
    action fu_F_7131_01 : FN_F_7131_01;
    action fu_F_7140_01 : FN_F_7140_01;
    action fu_F_7142_01 : FN_F_7142_01;
    action fu_F_7200_01 : FN_F_7200_01;
    action fu_F_7210_01 : FN_F_7210_01;
    action fu_F_7211_01 : FN_F_7211_01;
    action fu_F_7211_02 : FN_F_7211_02;
    action fu_F_7211_03 : FN_F_7211_03;
    action fu_F_7211_04 : FN_F_7211_04;
    action fu_F_7213_01 : FN_F_7213_01;
    action fu_F_7220_01 : FN_F_7220_01;
    action fu_F_7222_01 : FN_F_7222_01;
    action fu_F_7223_01 : FN_F_7223_01;
    action fu_F_7224_01 : FN_F_7224_01;
    action fu_F_7225_01 : FN_F_7225_01;
    action fu_F_7226_01 : FN_F_7226_01;
    action fu_F_7227_01 : FN_F_7227_01;
    action fu_F_7228_01 : FN_F_7228_01;
    action fu_F_7229_01 : FN_F_7229_01;
    action fu_F_722A_01 : FN_F_722A_01;
    action fu_F_722B_01 : FN_F_722B_01;
    action fu_F_722C_01 : FN_F_722C_01;
    action fu_F_7250_01 : FN_F_7250_01;
    action fu_F_7252_01 : FN_F_7252_01;
    action fu_F_7254_01 : FN_F_7254_01;
    action fu_F_7255_01 : FN_F_7255_01;
    action fu_F_7280_01 : FN_F_7280_01;
    action fu_F_7281_01 : FN_F_7281_01;
    action fu_F_7284_01 : FN_F_7284_01;
    action fu_F_7285_01 : FN_F_7285_01;
    action fu_F_8000_01 : FN_F_8000_01;
    action fu_F_8100_01 : FN_F_8100_01;
    action fu_F_8120_01 : FN_F_8120_01;
    action fu_F_8121_01 : FN_F_8121_01;
    action fu_F_8121_02 : FN_F_8121_02;
    action fu_F_8121_03 : FN_F_8121_03;
    action fu_F_8122_01 : FN_F_8122_01;
    action fu_F_8122_02 : FN_F_8122_02;
    action fu_F_8122_03 : FN_F_8122_03;
    action fu_F_8122_04 : FN_F_8122_04;
    action fu_F_8122_05 : FN_F_8122_05;
    action fu_F_8125_01 : FN_F_8125_01;
    action fu_F_8125_02 : FN_F_8125_02;
    action fu_F_8125_03 : FN_F_8125_03;
    action fu_F_8125_04 : FN_F_8125_04;
    action fu_F_8127_01 : FN_F_8127_01;
    action fu_F_8127_02 : FN_F_8127_02;
    action fu_F_8128_01 : FN_F_8128_01;
    action fu_F_8128_02 : FN_F_8128_02;
    action fu_F_8128_03 : FN_F_8128_03;
    action fu_F_8150_01 : FN_F_8150_01;
    action fu_F_8151_01 : FN_F_8151_01;
    action fu_F_8151_02 : FN_F_8151_02;
    action fu_F_8152_01 : FN_F_8152_01;
    action fu_F_8152_02 : FN_F_8152_02;
    action fu_F_8154_01 : FN_F_8154_01;
    action fu_F_8154_02 : FN_F_8154_02;
    action fu_F_8160_01 : FN_F_8160_01;
    action fu_F_8166_01 : FN_F_8166_01;
    action fu_F_8166_02 : FN_F_8166_02;
    action fu_F_8166_03 : FN_F_8166_03;
    action fu_F_8166_04 : FN_F_8166_04;
    action fu_F_D000_01 : FN_F_D000_01;
    action fu_F_D100_01 : FN_F_D100_01;
    action fu_F_D110_01 : FN_F_D110_01;
    action fu_F_D112_01 : FN_F_D112_01;
    action fu_F_D113_01 : FN_F_D113_01;
    action fu_F_D114_01 : FN_F_D114_01;
    action fu_F_D120_01 : FN_F_D120_01;
    action fu_F_D121_01 : FN_F_D121_01;
    action fu_F_D130_01 : FN_F_D130_01;
    action fu_F_D13B_01 : FN_F_D13B_01;
    action fu_F_E000_01 : FN_F_E000_01;
    action fu_F_E100_01 : FN_F_E100_01;
    action fu_F_X000_01 : FN_F_X000_01;
    action fu_F_X100_01 : FN_F_X100_01;
    action fu_F_X110_01 : FN_F_X110_01;
    action fu_F_X111_01 : FN_F_X111_01;
    action fu_F_X111_02 : FN_F_X111_02;
    action fu_F_X112_01 : FN_F_X112_01;
    action fu_F_X112_02 : FN_F_X112_02;
    action fu_F_X112_03 : FN_F_X112_03;
    action fu_F_X113_01 : FN_F_X113_01;
    action fu_F_X120_01 : FN_F_X120_01;
    action fu_F_X121_01 : FN_F_X121_01;
    action fu_F_X121_02 : FN_F_X121_02;
    action fu_F_X122_01 : FN_F_X122_01;
    action fu_F_X123_01 : FN_F_X123_01;
    action fu_F_X124_01 : FN_F_X124_01;
    action fu_F_X130_01 : FN_F_X130_01;
    action fu_F_X131_01 : FN_F_X131_01;
    action fu_F_X132_01 : FN_F_X132_01;
    action fu_F_X133_01 : FN_F_X133_01;
    part ap_N_3000 : P_N_3000;
    part ap_N_3100 : P_N_3100;
    part ap_N_3110 : P_N_3110;
    part ap_N_3111 : P_N_3111;
    part ap_N_3112 : P_N_3112;
    part ap_N_3120 : P_N_3120;
    part ap_N_3121 : P_N_3121;
    part ap_N_3130 : P_N_3130;
    part ap_N_3131 : P_N_3131;
    part ap_N_3132 : P_N_3132;
    part ap_N_3133 : P_N_3133;
    part ap_N_3500 : P_N_3500;
    part ap_N_3510 : P_N_3510;
    part ap_N_3511 : P_N_3511;
    part ap_N_3512 : P_N_3512;
    part ap_N_3514 : P_N_3514;
    part ap_N_3600 : P_N_3600;
    part ap_N_3640 : P_N_3640;
    part ap_N_3641 : P_N_3641;
    part ap_N_3643 : P_N_3643;
    part ap_N_3644 : P_N_3644;
    part ap_N_3800 : P_N_3800;
    part ap_N_3810 : P_N_3810;
    part ap_N_3811 : P_N_3811;
    part ap_N_3813 : P_N_3813;
    part ap_N_3814 : P_N_3814;
    part ap_N_4000 : P_N_4000;
    part ap_N_4100 : P_N_4100;
    part ap_N_4110 : P_N_4110;
    part ap_N_4111 : P_N_4111;
    part ap_N_411C : P_N_411C;
    part ap_N_4200 : P_N_4200;
    part ap_N_4210 : P_N_4210;
    part ap_N_4211 : P_N_4211;
    part ap_N_4212 : P_N_4212;
    part ap_N_4230 : P_N_4230;
    part ap_N_4235 : P_N_4235;
    part ap_N_4236 : P_N_4236;
    part ap_N_4238 : P_N_4238;
    part ap_N_4239 : P_N_4239;
    part ap_N_4240 : P_N_4240;
    part ap_N_4241 : P_N_4241;
    part ap_N_4400 : P_N_4400;
    part ap_N_4410 : P_N_4410;
    part ap_N_4411 : P_N_4411;
    part ap_N_4412 : P_N_4412;
    part ap_N_4413 : P_N_4413;
    part ap_N_4500 : P_N_4500;
    part ap_N_4510 : P_N_4510;
    part ap_N_4511 : P_N_4511;
    part ap_N_4513 : P_N_4513;
    part ap_N_4517 : P_N_4517;
    part ap_N_4518 : P_N_4518;
    part ap_N_5000 : P_N_5000;
    part ap_N_5100 : P_N_5100;
    part ap_N_5110 : P_N_5110;
    part ap_N_5111 : P_N_5111;
    part ap_N_5112 : P_N_5112;
    part ap_N_5113 : P_N_5113;
    part ap_N_5120 : P_N_5120;
    part ap_N_5121 : P_N_5121;
    part ap_N_5122 : P_N_5122;
    part ap_N_5130 : P_N_5130;
    part ap_N_5131 : P_N_5131;
    part ap_N_5132 : P_N_5132;
    part ap_N_5133 : P_N_5133;
    part ap_N_5140 : P_N_5140;
    part ap_N_5142 : P_N_5142;
    part ap_N_5145 : P_N_5145;
    part ap_N_5300 : P_N_5300;
    part ap_N_5310 : P_N_5310;
    part ap_N_5311 : P_N_5311;
    part ap_N_7000 : P_N_7000;
    part ap_N_7100 : P_N_7100;
    part ap_N_7120 : P_N_7120;
    part ap_N_7124 : P_N_7124;
    part ap_N_7130 : P_N_7130;
    part ap_N_7131 : P_N_7131;
    part ap_N_7140 : P_N_7140;
    part ap_N_7142 : P_N_7142;
    part ap_N_7200 : P_N_7200;
    part ap_N_7210 : P_N_7210;
    part ap_N_7211 : P_N_7211;
    part ap_N_7213 : P_N_7213;
    part ap_N_7220 : P_N_7220;
    part ap_N_7222 : P_N_7222;
    part ap_N_7223 : P_N_7223;
    part ap_N_7224 : P_N_7224;
    part ap_N_7225 : P_N_7225;
    part ap_N_7226 : P_N_7226;
    part ap_N_7227 : P_N_7227;
    part ap_N_7228 : P_N_7228;
    part ap_N_7229 : P_N_7229;
    part ap_N_722A : P_N_722A;
    part ap_N_722B : P_N_722B;
    part ap_N_722C : P_N_722C;
    part ap_N_7250 : P_N_7250;
    part ap_N_7252 : P_N_7252;
    part ap_N_7254 : P_N_7254;
    part ap_N_7255 : P_N_7255;
    part ap_N_7280 : P_N_7280;
    part ap_N_7281 : P_N_7281;
    part ap_N_7284 : P_N_7284;
    part ap_N_7285 : P_N_7285;
    part ap_N_8000 : P_N_8000;
    part ap_N_8100 : P_N_8100;
    part ap_N_8120 : P_N_8120;
    part ap_N_8121 : P_N_8121;
    part ap_N_8122 : P_N_8122;
    part ap_N_8125 : P_N_8125;
    part ap_N_8127 : P_N_8127;
    part ap_N_8128 : P_N_8128;
    part ap_N_8150 : P_N_8150;
    part ap_N_8151 : P_N_8151;
    part ap_N_8152 : P_N_8152;
    part ap_N_8154 : P_N_8154;
    part ap_N_8160 : P_N_8160;
    part ap_N_8166 : P_N_8166;
    part ap_D000 : P_D000;
    part ap_D100 : P_D100;
    part ap_D110 : P_D110;
    part ap_D112 : P_D112;
    part ap_D113 : P_D113;
    part ap_D114 : P_D114;
    part ap_D120 : P_D120;
    part ap_D121 : P_D121;
    part ap_D130 : P_D130;
    part ap_D13B : P_D13B;
    part ap_E000 : P_E000;
    part ap_E100 : P_E100;
    part ap_X000 : P_X000;
    part ap_X100 : P_X100;
    part ap_X110 : P_X110;
    part ap_X111 : P_X111;
    part ap_X112 : P_X112;
    part ap_X113 : P_X113;
    part ap_X120 : P_X120;
    part ap_X121 : P_X121;
    part ap_X122 : P_X122;
    part ap_X123 : P_X123;
    part ap_X124 : P_X124;
    part ap_X130 : P_X130;
    part ap_X131 : P_X131;
    part ap_X132 : P_X132;
    part ap_X133 : P_X133;
    allocation alloc_ALLOC_F_3000_01_3000 allocate fu_F_3000_01 to ap_N_3000;
    allocation alloc_ALLOC_F_3100_01_3100 allocate fu_F_3100_01 to ap_N_3100;
    allocation alloc_ALLOC_F_3110_01_3110 allocate fu_F_3110_01 to ap_N_3110;
    allocation alloc_ALLOC_F_3111_01_3111 allocate fu_F_3111_01 to ap_N_3111;
    allocation alloc_ALLOC_F_3112_01_3112 allocate fu_F_3112_01 to ap_N_3112;
    allocation alloc_ALLOC_F_3120_01_3120 allocate fu_F_3120_01 to ap_N_3120;
    allocation alloc_ALLOC_F_3121_01_3121 allocate fu_F_3121_01 to ap_N_3121;
    allocation alloc_ALLOC_F_3130_01_3130 allocate fu_F_3130_01 to ap_N_3130;
    allocation alloc_ALLOC_F_3131_01_3131 allocate fu_F_3131_01 to ap_N_3131;
    allocation alloc_ALLOC_F_3132_01_3132 allocate fu_F_3132_01 to ap_N_3132;
    allocation alloc_ALLOC_F_3133_01_3133 allocate fu_F_3133_01 to ap_N_3133;
    allocation alloc_ALLOC_F_3500_01_3500 allocate fu_F_3500_01 to ap_N_3500;
    allocation alloc_ALLOC_F_3510_01_3510 allocate fu_F_3510_01 to ap_N_3510;
    allocation alloc_ALLOC_F_3511_01_3511 allocate fu_F_3511_01 to ap_N_3511;
    allocation alloc_ALLOC_F_3512_01_3512 allocate fu_F_3512_01 to ap_N_3512;
    allocation alloc_ALLOC_F_3514_01_3514 allocate fu_F_3514_01 to ap_N_3514;
    allocation alloc_ALLOC_F_3600_01_3600 allocate fu_F_3600_01 to ap_N_3600;
    allocation alloc_ALLOC_F_3640_01_3640 allocate fu_F_3640_01 to ap_N_3640;
    allocation alloc_ALLOC_F_3641_01_3641 allocate fu_F_3641_01 to ap_N_3641;
    allocation alloc_ALLOC_F_3643_01_3643 allocate fu_F_3643_01 to ap_N_3643;
    allocation alloc_ALLOC_F_3644_01_3644 allocate fu_F_3644_01 to ap_N_3644;
    allocation alloc_ALLOC_F_3800_01_3800 allocate fu_F_3800_01 to ap_N_3800;
    allocation alloc_ALLOC_F_3810_01_3810 allocate fu_F_3810_01 to ap_N_3810;
    allocation alloc_ALLOC_F_3811_01_3811 allocate fu_F_3811_01 to ap_N_3811;
    allocation alloc_ALLOC_F_3811_02_3811 allocate fu_F_3811_02 to ap_N_3811;
    allocation alloc_ALLOC_F_3813_01_3813 allocate fu_F_3813_01 to ap_N_3813;
    allocation alloc_ALLOC_F_3814_01_3814 allocate fu_F_3814_01 to ap_N_3814;
    allocation alloc_ALLOC_F_4000_01_4000 allocate fu_F_4000_01 to ap_N_4000;
    allocation alloc_ALLOC_F_4100_01_4100 allocate fu_F_4100_01 to ap_N_4100;
    allocation alloc_ALLOC_F_4110_01_4110 allocate fu_F_4110_01 to ap_N_4110;
    allocation alloc_ALLOC_F_4111_01_4111 allocate fu_F_4111_01 to ap_N_4111;
    allocation alloc_ALLOC_F_411C_01_411C allocate fu_F_411C_01 to ap_N_411C;
    allocation alloc_ALLOC_F_411C_02_411C allocate fu_F_411C_02 to ap_N_411C;
    allocation alloc_ALLOC_F_4200_01_4200 allocate fu_F_4200_01 to ap_N_4200;
    allocation alloc_ALLOC_F_4210_01_4210 allocate fu_F_4210_01 to ap_N_4210;
    allocation alloc_ALLOC_F_4211_01_4211 allocate fu_F_4211_01 to ap_N_4211;
    allocation alloc_ALLOC_F_4212_01_4212 allocate fu_F_4212_01 to ap_N_4212;
    allocation alloc_ALLOC_F_4230_01_4230 allocate fu_F_4230_01 to ap_N_4230;
    allocation alloc_ALLOC_F_4235_01_4235 allocate fu_F_4235_01 to ap_N_4235;
    allocation alloc_ALLOC_F_4236_01_4236 allocate fu_F_4236_01 to ap_N_4236;
    allocation alloc_ALLOC_F_4238_01_4238 allocate fu_F_4238_01 to ap_N_4238;
    allocation alloc_ALLOC_F_4238_02_4238 allocate fu_F_4238_02 to ap_N_4238;
    allocation alloc_ALLOC_F_4238_03_4238 allocate fu_F_4238_03 to ap_N_4238;
    allocation alloc_ALLOC_F_4239_01_4239 allocate fu_F_4239_01 to ap_N_4239;
    allocation alloc_ALLOC_F_4239_02_4239 allocate fu_F_4239_02 to ap_N_4239;
    allocation alloc_ALLOC_F_4239_03_4239 allocate fu_F_4239_03 to ap_N_4239;
    allocation alloc_ALLOC_F_4240_01_4240 allocate fu_F_4240_01 to ap_N_4240;
    allocation alloc_ALLOC_F_4241_01_4241 allocate fu_F_4241_01 to ap_N_4241;
    allocation alloc_ALLOC_F_4241_02_4241 allocate fu_F_4241_02 to ap_N_4241;
    allocation alloc_ALLOC_F_4241_03_4241 allocate fu_F_4241_03 to ap_N_4241;
    allocation alloc_ALLOC_F_4400_01_4400 allocate fu_F_4400_01 to ap_N_4400;
    allocation alloc_ALLOC_F_4410_01_4410 allocate fu_F_4410_01 to ap_N_4410;
    allocation alloc_ALLOC_F_4411_01_4411 allocate fu_F_4411_01 to ap_N_4411;
    allocation alloc_ALLOC_F_4412_01_4412 allocate fu_F_4412_01 to ap_N_4412;
    allocation alloc_ALLOC_F_4413_01_4413 allocate fu_F_4413_01 to ap_N_4413;
    allocation alloc_ALLOC_F_4500_01_4500 allocate fu_F_4500_01 to ap_N_4500;
    allocation alloc_ALLOC_F_4510_01_4510 allocate fu_F_4510_01 to ap_N_4510;
    allocation alloc_ALLOC_F_4511_01_4511 allocate fu_F_4511_01 to ap_N_4511;
    allocation alloc_ALLOC_F_4513_01_4513 allocate fu_F_4513_01 to ap_N_4513;
    allocation alloc_ALLOC_F_4517_01_4517 allocate fu_F_4517_01 to ap_N_4517;
    allocation alloc_ALLOC_F_4518_01_4518 allocate fu_F_4518_01 to ap_N_4518;
    allocation alloc_ALLOC_F_4518_02_4518 allocate fu_F_4518_02 to ap_N_4518;
    allocation alloc_ALLOC_F_5000_01_5000 allocate fu_F_5000_01 to ap_N_5000;
    allocation alloc_ALLOC_F_5100_01_5100 allocate fu_F_5100_01 to ap_N_5100;
    allocation alloc_ALLOC_F_5110_01_5110 allocate fu_F_5110_01 to ap_N_5110;
    allocation alloc_ALLOC_F_5111_01_5111 allocate fu_F_5111_01 to ap_N_5111;
    allocation alloc_ALLOC_F_5111_02_5111 allocate fu_F_5111_02 to ap_N_5111;
    allocation alloc_ALLOC_F_5111_03_5111 allocate fu_F_5111_03 to ap_N_5111;
    allocation alloc_ALLOC_F_5111_04_5111 allocate fu_F_5111_04 to ap_N_5111;
    allocation alloc_ALLOC_F_5112_01_5112 allocate fu_F_5112_01 to ap_N_5112;
    allocation alloc_ALLOC_F_5112_02_5112 allocate fu_F_5112_02 to ap_N_5112;
    allocation alloc_ALLOC_F_5112_03_5112 allocate fu_F_5112_03 to ap_N_5112;
    allocation alloc_ALLOC_F_5112_04_5112 allocate fu_F_5112_04 to ap_N_5112;
    allocation alloc_ALLOC_F_5113_01_5113 allocate fu_F_5113_01 to ap_N_5113;
    allocation alloc_ALLOC_F_5120_01_5120 allocate fu_F_5120_01 to ap_N_5120;
    allocation alloc_ALLOC_F_5121_01_5121 allocate fu_F_5121_01 to ap_N_5121;
    allocation alloc_ALLOC_F_5122_01_5122 allocate fu_F_5122_01 to ap_N_5122;
    allocation alloc_ALLOC_F_5130_01_5130 allocate fu_F_5130_01 to ap_N_5130;
    allocation alloc_ALLOC_F_5131_01_5131 allocate fu_F_5131_01 to ap_N_5131;
    allocation alloc_ALLOC_F_5131_02_5131 allocate fu_F_5131_02 to ap_N_5131;
    allocation alloc_ALLOC_F_5132_01_5132 allocate fu_F_5132_01 to ap_N_5132;
    allocation alloc_ALLOC_F_5132_02_5132 allocate fu_F_5132_02 to ap_N_5132;
    allocation alloc_ALLOC_F_5133_01_5133 allocate fu_F_5133_01 to ap_N_5133;
    allocation alloc_ALLOC_F_5133_02_5133 allocate fu_F_5133_02 to ap_N_5133;
    allocation alloc_ALLOC_F_5133_03_5133 allocate fu_F_5133_03 to ap_N_5133;
    allocation alloc_ALLOC_F_5140_01_5140 allocate fu_F_5140_01 to ap_N_5140;
    allocation alloc_ALLOC_F_5142_01_5142 allocate fu_F_5142_01 to ap_N_5142;
    allocation alloc_ALLOC_F_5142_02_5142 allocate fu_F_5142_02 to ap_N_5142;
    allocation alloc_ALLOC_F_5145_01_5145 allocate fu_F_5145_01 to ap_N_5145;
    allocation alloc_ALLOC_F_5300_01_5300 allocate fu_F_5300_01 to ap_N_5300;
    allocation alloc_ALLOC_F_5310_01_5310 allocate fu_F_5310_01 to ap_N_5310;
    allocation alloc_ALLOC_F_5311_01_5311 allocate fu_F_5311_01 to ap_N_5311;
    allocation alloc_ALLOC_F_5311_02_5311 allocate fu_F_5311_02 to ap_N_5311;
    allocation alloc_ALLOC_F_7000_01_7000 allocate fu_F_7000_01 to ap_N_7000;
    allocation alloc_ALLOC_F_7100_01_7100 allocate fu_F_7100_01 to ap_N_7100;
    allocation alloc_ALLOC_F_7120_01_7120 allocate fu_F_7120_01 to ap_N_7120;
    allocation alloc_ALLOC_F_7124_01_7124 allocate fu_F_7124_01 to ap_N_7124;
    allocation alloc_ALLOC_F_7130_01_7130 allocate fu_F_7130_01 to ap_N_7130;
    allocation alloc_ALLOC_F_7131_01_7131 allocate fu_F_7131_01 to ap_N_7131;
    allocation alloc_ALLOC_F_7140_01_7140 allocate fu_F_7140_01 to ap_N_7140;
    allocation alloc_ALLOC_F_7142_01_7142 allocate fu_F_7142_01 to ap_N_7142;
    allocation alloc_ALLOC_F_7200_01_7200 allocate fu_F_7200_01 to ap_N_7200;
    allocation alloc_ALLOC_F_7210_01_7210 allocate fu_F_7210_01 to ap_N_7210;
    allocation alloc_ALLOC_F_7211_01_7211 allocate fu_F_7211_01 to ap_N_7211;
    allocation alloc_ALLOC_F_7211_02_7211 allocate fu_F_7211_02 to ap_N_7211;
    allocation alloc_ALLOC_F_7211_03_7211 allocate fu_F_7211_03 to ap_N_7211;
    allocation alloc_ALLOC_F_7211_04_7211 allocate fu_F_7211_04 to ap_N_7211;
    allocation alloc_ALLOC_F_7213_01_7213 allocate fu_F_7213_01 to ap_N_7213;
    allocation alloc_ALLOC_F_7220_01_7220 allocate fu_F_7220_01 to ap_N_7220;
    allocation alloc_ALLOC_F_7222_01_7222 allocate fu_F_7222_01 to ap_N_7222;
    allocation alloc_ALLOC_F_7223_01_7223 allocate fu_F_7223_01 to ap_N_7223;
    allocation alloc_ALLOC_F_7224_01_7224 allocate fu_F_7224_01 to ap_N_7224;
    allocation alloc_ALLOC_F_7225_01_7225 allocate fu_F_7225_01 to ap_N_7225;
    allocation alloc_ALLOC_F_7226_01_7226 allocate fu_F_7226_01 to ap_N_7226;
    allocation alloc_ALLOC_F_7227_01_7227 allocate fu_F_7227_01 to ap_N_7227;
    allocation alloc_ALLOC_F_7228_01_7228 allocate fu_F_7228_01 to ap_N_7228;
    allocation alloc_ALLOC_F_7229_01_7229 allocate fu_F_7229_01 to ap_N_7229;
    allocation alloc_ALLOC_F_722A_01_722A allocate fu_F_722A_01 to ap_N_722A;
    allocation alloc_ALLOC_F_722B_01_722B allocate fu_F_722B_01 to ap_N_722B;
    allocation alloc_ALLOC_F_722C_01_722C allocate fu_F_722C_01 to ap_N_722C;
    allocation alloc_ALLOC_F_7250_01_7250 allocate fu_F_7250_01 to ap_N_7250;
    allocation alloc_ALLOC_F_7252_01_7252 allocate fu_F_7252_01 to ap_N_7252;
    allocation alloc_ALLOC_F_7254_01_7254 allocate fu_F_7254_01 to ap_N_7254;
    allocation alloc_ALLOC_F_7255_01_7255 allocate fu_F_7255_01 to ap_N_7255;
    allocation alloc_ALLOC_F_7280_01_7280 allocate fu_F_7280_01 to ap_N_7280;
    allocation alloc_ALLOC_F_7281_01_7281 allocate fu_F_7281_01 to ap_N_7281;
    allocation alloc_ALLOC_F_7284_01_7284 allocate fu_F_7284_01 to ap_N_7284;
    allocation alloc_ALLOC_F_7285_01_7285 allocate fu_F_7285_01 to ap_N_7285;
    allocation alloc_ALLOC_F_8000_01_8000 allocate fu_F_8000_01 to ap_N_8000;
    allocation alloc_ALLOC_F_8100_01_8100 allocate fu_F_8100_01 to ap_N_8100;
    allocation alloc_ALLOC_F_8120_01_8120 allocate fu_F_8120_01 to ap_N_8120;
    allocation alloc_ALLOC_F_8121_01_8121 allocate fu_F_8121_01 to ap_N_8121;
    allocation alloc_ALLOC_F_8121_02_8121 allocate fu_F_8121_02 to ap_N_8121;
    allocation alloc_ALLOC_F_8121_03_8121 allocate fu_F_8121_03 to ap_N_8121;
    allocation alloc_ALLOC_F_8122_01_8122 allocate fu_F_8122_01 to ap_N_8122;
    allocation alloc_ALLOC_F_8122_02_8122 allocate fu_F_8122_02 to ap_N_8122;
    allocation alloc_ALLOC_F_8122_03_8122 allocate fu_F_8122_03 to ap_N_8122;
    allocation alloc_ALLOC_F_8122_04_8122 allocate fu_F_8122_04 to ap_N_8122;
    allocation alloc_ALLOC_F_8122_05_8122 allocate fu_F_8122_05 to ap_N_8122;
    allocation alloc_ALLOC_F_8125_01_8125 allocate fu_F_8125_01 to ap_N_8125;
    allocation alloc_ALLOC_F_8125_02_8125 allocate fu_F_8125_02 to ap_N_8125;
    allocation alloc_ALLOC_F_8125_03_8125 allocate fu_F_8125_03 to ap_N_8125;
    allocation alloc_ALLOC_F_8125_04_8125 allocate fu_F_8125_04 to ap_N_8125;
    allocation alloc_ALLOC_F_8127_01_8127 allocate fu_F_8127_01 to ap_N_8127;
    allocation alloc_ALLOC_F_8127_02_8127 allocate fu_F_8127_02 to ap_N_8127;
    allocation alloc_ALLOC_F_8128_01_8128 allocate fu_F_8128_01 to ap_N_8128;
    allocation alloc_ALLOC_F_8128_02_8128 allocate fu_F_8128_02 to ap_N_8128;
    allocation alloc_ALLOC_F_8128_03_8128 allocate fu_F_8128_03 to ap_N_8128;
    allocation alloc_ALLOC_F_8150_01_8150 allocate fu_F_8150_01 to ap_N_8150;
    allocation alloc_ALLOC_F_8151_01_8151 allocate fu_F_8151_01 to ap_N_8151;
    allocation alloc_ALLOC_F_8151_02_8151 allocate fu_F_8151_02 to ap_N_8151;
    allocation alloc_ALLOC_F_8152_01_8152 allocate fu_F_8152_01 to ap_N_8152;
    allocation alloc_ALLOC_F_8152_02_8152 allocate fu_F_8152_02 to ap_N_8152;
    allocation alloc_ALLOC_F_8154_01_8154 allocate fu_F_8154_01 to ap_N_8154;
    allocation alloc_ALLOC_F_8154_02_8154 allocate fu_F_8154_02 to ap_N_8154;
    allocation alloc_ALLOC_F_8160_01_8160 allocate fu_F_8160_01 to ap_N_8160;
    allocation alloc_ALLOC_F_8166_01_8166 allocate fu_F_8166_01 to ap_N_8166;
    allocation alloc_ALLOC_F_8166_02_8166 allocate fu_F_8166_02 to ap_N_8166;
    allocation alloc_ALLOC_F_8166_03_8166 allocate fu_F_8166_03 to ap_N_8166;
    allocation alloc_ALLOC_F_8166_04_8166 allocate fu_F_8166_04 to ap_N_8166;
    allocation alloc_ALLOC_F_D000_01_D000 allocate fu_F_D000_01 to ap_D000;
    allocation alloc_ALLOC_F_D100_01_D100 allocate fu_F_D100_01 to ap_D100;
    allocation alloc_ALLOC_F_D110_01_D110 allocate fu_F_D110_01 to ap_D110;
    allocation alloc_ALLOC_F_D112_01_D112 allocate fu_F_D112_01 to ap_D112;
    allocation alloc_ALLOC_F_D113_01_D113 allocate fu_F_D113_01 to ap_D113;
    allocation alloc_ALLOC_F_D114_01_D114 allocate fu_F_D114_01 to ap_D114;
    allocation alloc_ALLOC_F_D120_01_D120 allocate fu_F_D120_01 to ap_D120;
    allocation alloc_ALLOC_F_D121_01_D121 allocate fu_F_D121_01 to ap_D121;
    allocation alloc_ALLOC_F_D130_01_D130 allocate fu_F_D130_01 to ap_D130;
    allocation alloc_ALLOC_F_D13B_01_D13B allocate fu_F_D13B_01 to ap_D13B;
    allocation alloc_ALLOC_F_E000_01_E000 allocate fu_F_E000_01 to ap_E000;
    allocation alloc_ALLOC_F_E100_01_E100 allocate fu_F_E100_01 to ap_E100;
    allocation alloc_ALLOC_F_X000_01_X000 allocate fu_F_X000_01 to ap_X000;
    allocation alloc_ALLOC_F_X100_01_X100 allocate fu_F_X100_01 to ap_X100;
    allocation alloc_ALLOC_F_X110_01_X110 allocate fu_F_X110_01 to ap_X110;
    allocation alloc_ALLOC_F_X111_01_X111 allocate fu_F_X111_01 to ap_X111;
    allocation alloc_ALLOC_F_X111_02_X111 allocate fu_F_X111_02 to ap_X111;
    allocation alloc_ALLOC_F_X112_01_X112 allocate fu_F_X112_01 to ap_X112;
    allocation alloc_ALLOC_F_X112_02_X112 allocate fu_F_X112_02 to ap_X112;
    allocation alloc_ALLOC_F_X112_03_X112 allocate fu_F_X112_03 to ap_X112;
    allocation alloc_ALLOC_F_X113_01_X113 allocate fu_F_X113_01 to ap_X113;
    allocation alloc_ALLOC_F_X120_01_X120 allocate fu_F_X120_01 to ap_X120;
    allocation alloc_ALLOC_F_X121_01_X121 allocate fu_F_X121_01 to ap_X121;
    allocation alloc_ALLOC_F_X121_02_X121 allocate fu_F_X121_02 to ap_X121;
    allocation alloc_ALLOC_F_X122_01_X122 allocate fu_F_X122_01 to ap_X122;
    allocation alloc_ALLOC_F_X123_01_X123 allocate fu_F_X123_01 to ap_X123;
    allocation alloc_ALLOC_F_X124_01_X124 allocate fu_F_X124_01 to ap_X124;
    allocation alloc_ALLOC_F_X130_01_X130 allocate fu_F_X130_01 to ap_X130;
    allocation alloc_ALLOC_F_X131_01_X131 allocate fu_F_X131_01 to ap_X131;
    allocation alloc_ALLOC_F_X132_01_X132 allocate fu_F_X132_01 to ap_X132;
    allocation alloc_ALLOC_F_X133_01_X133 allocate fu_F_X133_01 to ap_X133;
}

package PhysicalNetworks {
    private import ScalarValues::*;
    private import ProductDefinitions::*;
    part physicalNetworkContext : RailSystemContext {
        connection net_NET_DC_LINK_01 connect (p_N_5000.p_N_5100.p_N_5120.p_N_5121.rp_e5b052bb75ba8a31, p_N_5000.p_N_5100.p_N_5120.p_N_5122.rp_6e156eb66bd95a75, p_N_5000.p_N_5100.p_N_5130.p_N_5131.rp_f010ea68f7dddd01, p_N_5000.p_N_5100.p_N_5130.p_N_5132.rp_e9be022214796a74, p_N_5000.p_N_5100.p_N_5140.p_N_5142.rp_14fbc389883862a8, p_X000.p_X100.p_X110.p_X111.rp_565c4036e651287e, p_X000.p_X100.p_X110.p_X113.rp_571e6f079e1116ac) {
            attribute netId : String = "NET-DC-LINK-01";
            attribute itemCode : String = "ITM-PHY-003";
        }
        connection net_NET_LVDC_CONTROL_01 connect (p_N_3000.p_N_3800.p_N_3810.p_N_3811.rp_ad36be2404e763eb, p_N_4000.p_N_4100.p_N_4110.p_N_411C.rp_d6a2171160c4b693, p_N_4000.p_N_4200.p_N_4230.p_N_4238.rp_dc173bda6489186d, p_N_4000.p_N_4200.p_N_4230.p_N_4239.rp_9c4bbbf0c73d853e, p_N_4000.p_N_4200.p_N_4240.p_N_4241.rp_efc0e0ead5465ae4, p_N_4000.p_N_4500.p_N_4510.p_N_4517.rp_fa22ceafa52cda89, p_N_4000.p_N_4500.p_N_4510.p_N_4518.rp_950aee7777f5ea28, p_N_5000.p_N_5100.p_N_5110.p_N_5111.rp_9ceb0295e403e673, p_N_5000.p_N_5100.p_N_5110.p_N_5112.rp_c60f875ac7e265d0, p_N_5000.p_N_5100.p_N_5110.p_N_5113.rp_6f5e3f6e1f0f9b1a, p_N_5000.p_N_5100.p_N_5130.p_N_5133.rp_b97ef71e558464ef, p_N_5000.p_N_5100.p_N_5140.p_N_5145.rp_b22756bb5d4e9b69, p_N_7000.p_N_7200.p_N_7210.p_N_7211.rp_b34d5a11f0a32260, p_N_7000.p_N_7200.p_N_7210.p_N_7213.rp_de41681b082603dc, p_N_7000.p_N_7200.p_N_7280.p_N_7281.rp_2e35e3bc261ab52a, p_N_8000.p_N_8100.p_N_8120.p_N_8121.rp_d2dfdd1f41baec7a, p_N_8000.p_N_8100.p_N_8120.p_N_8122.rp_8b55477454952732, p_N_8000.p_N_8100.p_N_8120.p_N_8125.rp_5184547f4558dae5, p_N_8000.p_N_8100.p_N_8120.p_N_8127.rp_903b55a0b6383446, p_N_8000.p_N_8100.p_N_8120.p_N_8128.rp_3b5ccced6e75cf2c, p_N_8000.p_N_8100.p_N_8150.p_N_8151.rp_b128738a40d9fcd8, p_N_8000.p_N_8100.p_N_8150.p_N_8152.rp_1e9ebcfb3cef3e9d, p_N_8000.p_N_8100.p_N_8150.p_N_8154.rp_caee94e6ee66a74d, p_N_8000.p_N_8100.p_N_8160.p_N_8166.rp_937652db70f809a4, p_X000.p_X100.p_X110.p_X112.rp_569130817376da24, p_X000.p_X100.p_X110.p_X113.rp_9f0c62635f9ae105, p_X000.p_X100.p_X130.p_X133.rp_da93423081013940) {
            attribute netId : String = "NET-LVDC-CONTROL-01";
            attribute itemCode : String = "ITM-PHY-015";
        }
        connection net_NET_MAIN_RETURN_01 connect (p_N_4000.p_N_4400.p_N_4410.p_N_4411.rp_45b0eaf9bb476ccf, p_N_4000.p_N_4400.p_N_4410.p_N_4411.rp_5e63cd1bffa78a41, p_N_4000.p_N_4400.p_N_4410.p_N_4412.rp_e2c805a6993ee3dc, p_N_4000.p_N_4400.p_N_4410.p_N_4412.rp_f330d9bb72a522df, p_N_4000.p_N_4400.p_N_4410.p_N_4413.rp_c808ea5883784df8) {
            attribute netId : String = "NET-MAIN-RETURN-01";
            attribute itemCode : String = "ITM-PHY-011";
        }
        connection net_NET_PNEU_BRAKE_SUPPLY_01 connect (p_N_7000.p_N_7200.p_N_7220.p_N_7222.rp_43816dbefe351165, p_N_7000.p_N_7200.p_N_7220.p_N_7223.rp_9441f85d6ac8b0ed, p_N_7000.p_N_7200.p_N_7220.p_N_7224.rp_0714bcd5930c027b, p_N_7000.p_N_7200.p_N_7220.p_N_7225.rp_99bc109c3b70dfed, p_N_7000.p_N_7200.p_N_7220.p_N_7226.rp_0f31359846cbf234, p_N_7000.p_N_7200.p_N_7220.p_N_7229.rp_a8a0abe4af23248d) {
            attribute netId : String = "NET-PNEU-BRAKE-SUPPLY-01";
            attribute itemCode : String = "ITM-PHY-009";
        }
        connection net_NET_PNEU_CYLINDER_01 connect (p_N_7000.p_N_7200.p_N_7220.p_N_7223.rp_26b22e117179b62a, p_N_7000.p_N_7200.p_N_7220.p_N_7226.rp_afce9ce1d2c43605, p_N_7000.p_N_7200.p_N_7220.p_N_7227.rp_26311db59efd1104, p_N_7000.p_N_7200.p_N_7220.p_N_7228.rp_9f256ce20a2eedba, p_N_7000.p_N_7200.p_N_7220.p_N_7228.rp_e8a2cfb94eeae29a, p_N_7000.p_N_7200.p_N_7220.p_N_722A.rp_0093bc65af2a8f0a, p_N_7000.p_N_7200.p_N_7220.p_N_722A.rp_1d96067b68d03c9c, p_N_7000.p_N_7200.p_N_7220.p_N_722B.rp_4861b172f136b92e, p_N_7000.p_N_7200.p_N_7220.p_N_722C.rp_041b8e496fc7f6c1, p_N_7000.p_N_7200.p_N_7250.p_N_7252.rp_7e02e65996d4ca82, p_N_7000.p_N_7200.p_N_7250.p_N_7255.rp_734246fb536f2b68, p_N_7000.p_N_7200.p_N_7280.p_N_7284.rp_3e963340985cb7bd, p_N_7000.p_N_7200.p_N_7280.p_N_7284.rp_c958e15a33eb790f, p_N_7000.p_N_7200.p_N_7280.p_N_7285.rp_337ee35177e1c114, p_N_7000.p_N_7200.p_N_7280.p_N_7285.rp_73c5051041203267) {
            attribute netId : String = "NET-PNEU-CYLINDER-01";
            attribute itemCode : String = "ITM-PHY-010";
        }
        connection net_NET_PNEU_MAIN_01 connect (p_N_3000.p_N_3800.p_N_3810.p_N_3813.rp_3f7e961856b812d2, p_N_7000.p_N_7100.p_N_7120.p_N_7124.rp_732b5a3acb4e2be0, p_N_7000.p_N_7100.p_N_7130.p_N_7131.rp_e275cbf47ef42c02, p_N_7000.p_N_7100.p_N_7130.p_N_7131.rp_e73ffca5021e0883, p_N_7000.p_N_7100.p_N_7140.p_N_7142.rp_b1c762907b90d07b, p_N_7000.p_N_7200.p_N_7220.p_N_7222.rp_d9d50ab5a08a26a5, p_N_7000.p_N_7200.p_N_7220.p_N_7223.rp_4abc41bc202f61af, p_N_7000.p_N_7200.p_N_7220.p_N_7224.rp_291ee811748691f6, p_N_7000.p_N_7200.p_N_7220.p_N_7225.rp_f6a9fd98bacfc4e3, p_N_7000.p_N_7200.p_N_7220.p_N_7226.rp_5cccca40a5c3ac4f, p_N_7000.p_N_7200.p_N_7220.p_N_7229.rp_b38d34e10f750709) {
            attribute netId : String = "NET-PNEU-MAIN-01";
            attribute itemCode : String = "ITM-PHY-008";
        }
        connection net_NET_STORAGE_DC_AFTER_CONTACTOR_01 connect (p_X000.p_X100.p_X130.p_X131.rp_6bdc28fa4761142d, p_X000.p_X100.p_X130.p_X132.rp_1d9e411fc4e0ebf9, p_X000.p_X100.p_X130.p_X133.rp_06282bbd1af76861) {
            attribute netId : String = "NET-STORAGE-DC-AFTER-CONTACTOR-01";
            attribute itemCode : String = "ITM-PHY-016";
        }
        connection net_NET_STORAGE_DC_BUS_01 connect (p_X000.p_X100.p_X110.p_X111.rp_f6cc38ed3ebf357f, p_X000.p_X100.p_X110.p_X113.rp_5e8b7419342ecb12, p_X000.p_X100.p_X130.p_X131.rp_ef3e7082da0c5648, p_X000.p_X100.p_X130.p_X132.rp_0fa709507856ec0b) {
            attribute netId : String = "NET-STORAGE-DC-BUS-01";
            attribute itemCode : String = "ITM-PHY-016";
        }
        connection net_NET_STORAGE_DC_SC_01 connect (p_X000.p_X100.p_X120.p_X121.rp_e7b0b50420861015, p_X000.p_X100.p_X120.p_X122.rp_0b3c69b37f8b252c, p_X000.p_X100.p_X120.p_X123.rp_b6c8109cae13eea5, p_X000.p_X100.p_X130.p_X133.rp_49a2b1a2497ebf63) {
            attribute netId : String = "NET-STORAGE-DC-SC-01";
            attribute itemCode : String = "ITM-PHY-016";
        }
    }
}

package Traceability {
    private import ScalarValues::*;
    item def TraceRecord { attribute elementId : String; attribute sourceFile : String; attribute sourceSheet : String; attribute sourceRow : Integer; }
    item trace_16f66728bb355fce : TraceRecord {
        attribute :>> elementId = "DEF::3000";
        attribute :>> sourceFile = "Rail_MBSE_Function_Interface_v1_final.xlsx";
        attribute :>> sourceSheet = "Product_Hierarchy";
        attribute :>> sourceRow = 5;
    }
    item trace_d9ec1ca9bc5239ef : TraceRecord {
        attribute :>> elementId = "USAGE::3000";
        attribute :>> sourceFile = "Rail_MBSE_Function_Interface_v1_final.xlsx";
        attribute :>> sourceSheet = "Product_Hierarchy";
        attribute :>> sourceRow = 5;
    }
    item trace_fcb483f0877f3b96 : TraceRecord {
        attribute :>> elementId = "DEF::4000";
        attribute :>> sourceFile = "Rail_MBSE_Function_Interface_v1_final.xlsx";
        attribute :>> sourceSheet = "Product_Hierarchy";
        attribute :>> sourceRow = 6;
    }
    item trace_33789d2be35ddbcb : TraceRecord {
        attribute :>> elementId = "USAGE::4000";
        attribute :>> sourceFile = "Rail_MBSE_Function_Interface_v1_final.xlsx";
        attribute :>> sourceSheet = "Product_Hierarchy";
        attribute :>> sourceRow = 6;
    }
    item trace_ed868e9719d8959d : TraceRecord {
        attribute :>> elementId = "DEF::5000";
        attribute :>> sourceFile = "Rail_MBSE_Function_Interface_v1_final.xlsx";
        attribute :>> sourceSheet = "Product_Hierarchy";
        attribute :>> sourceRow = 7;
    }
    item trace_2583aac1161743ea : TraceRecord {
        attribute :>> elementId = "USAGE::5000";
        attribute :>> sourceFile = "Rail_MBSE_Function_Interface_v1_final.xlsx";
        attribute :>> sourceSheet = "Product_Hierarchy";
        attribute :>> sourceRow = 7;
    }
    item trace_88732f7d895a1f5d : TraceRecord {
        attribute :>> elementId = "DEF::7000";
        attribute :>> sourceFile = "Rail_MBSE_Function_Interface_v1_final.xlsx";
        attribute :>> sourceSheet = "Product_Hierarchy";
        attribute :>> sourceRow = 8;
    }
    item trace_d989aba0c853b507 : TraceRecord {
        attribute :>> elementId = "USAGE::7000";
        attribute :>> sourceFile = "Rail_MBSE_Function_Interface_v1_final.xlsx";
        attribute :>> sourceSheet = "Product_Hierarchy";
        attribute :>> sourceRow = 8;
    }
    item trace_9293b2e1faba62fc : TraceRecord {
        attribute :>> elementId = "DEF::8000";
        attribute :>> sourceFile = "Rail_MBSE_Function_Interface_v1_final.xlsx";
        attribute :>> sourceSheet = "Product_Hierarchy";
        attribute :>> sourceRow = 9;
    }
    item trace_9189a90e5ed7f545 : TraceRecord {
        attribute :>> elementId = "USAGE::8000";
        attribute :>> sourceFile = "Rail_MBSE_Function_Interface_v1_final.xlsx";
        attribute :>> sourceSheet = "Product_Hierarchy";
        attribute :>> sourceRow = 9;
    }
    item trace_c013ab1280ef51e4 : TraceRecord {
        attribute :>> elementId = "DEF::D000";
        attribute :>> sourceFile = "Rail_MBSE_Function_Interface_v1_final.xlsx";
        attribute :>> sourceSheet = "Product_Hierarchy";
        attribute :>> sourceRow = 10;
    }
    item trace_324b1453212d5b11 : TraceRecord {
        attribute :>> elementId = "USAGE::D000";
        attribute :>> sourceFile = "Rail_MBSE_Function_Interface_v1_final.xlsx";
        attribute :>> sourceSheet = "Product_Hierarchy";
        attribute :>> sourceRow = 10;
    }
    item trace_68c679c7a3ffb599 : TraceRecord {
        attribute :>> elementId = "DEF::E000";
        attribute :>> sourceFile = "Rail_MBSE_Function_Interface_v1_final.xlsx";
        attribute :>> sourceSheet = "Product_Hierarchy";
        attribute :>> sourceRow = 11;
    }
    item trace_96d66d3bfcdcaf5f : TraceRecord {
        attribute :>> elementId = "USAGE::E000";
        attribute :>> sourceFile = "Rail_MBSE_Function_Interface_v1_final.xlsx";
        attribute :>> sourceSheet = "Product_Hierarchy";
        attribute :>> sourceRow = 11;
    }
    item trace_acd0a6aa5711d419 : TraceRecord {
        attribute :>> elementId = "DEF::X000";
        attribute :>> sourceFile = "Rail_MBSE_Function_Interface_v1_final.xlsx";
        attribute :>> sourceSheet = "Product_Hierarchy";
        attribute :>> sourceRow = 12;
    }
    item trace_6db44849eea2206c : TraceRecord {
        attribute :>> elementId = "USAGE::X000";
        attribute :>> sourceFile = "Rail_MBSE_Function_Interface_v1_final.xlsx";
        attribute :>> sourceSheet = "Product_Hierarchy";
        attribute :>> sourceRow = 12;
    }
    item trace_5dbc9f108b295b7a : TraceRecord {
        attribute :>> elementId = "DEF::3100";
        attribute :>> sourceFile = "Rail_MBSE_Function_Interface_v1_final.xlsx";
        attribute :>> sourceSheet = "Product_Hierarchy";
        attribute :>> sourceRow = 13;
    }
    item trace_a1816d9db1adc823 : TraceRecord {
        attribute :>> elementId = "USAGE::3100";
        attribute :>> sourceFile = "Rail_MBSE_Function_Interface_v1_final.xlsx";
        attribute :>> sourceSheet = "Product_Hierarchy";
        attribute :>> sourceRow = 13;
    }
    item trace_c1f4f88d747a2ce7 : TraceRecord {
        attribute :>> elementId = "DEF::3500";
        attribute :>> sourceFile = "Rail_MBSE_Function_Interface_v1_final.xlsx";
        attribute :>> sourceSheet = "Product_Hierarchy";
        attribute :>> sourceRow = 14;
    }
    item trace_9962b08c6aff5249 : TraceRecord {
        attribute :>> elementId = "USAGE::3500";
        attribute :>> sourceFile = "Rail_MBSE_Function_Interface_v1_final.xlsx";
        attribute :>> sourceSheet = "Product_Hierarchy";
        attribute :>> sourceRow = 14;
    }
    item trace_a0f46d8b96b02e4e : TraceRecord {
        attribute :>> elementId = "DEF::3600";
        attribute :>> sourceFile = "Rail_MBSE_Function_Interface_v1_final.xlsx";
        attribute :>> sourceSheet = "Product_Hierarchy";
        attribute :>> sourceRow = 15;
    }
    item trace_c9355167b35d78d5 : TraceRecord {
        attribute :>> elementId = "USAGE::3600";
        attribute :>> sourceFile = "Rail_MBSE_Function_Interface_v1_final.xlsx";
        attribute :>> sourceSheet = "Product_Hierarchy";
        attribute :>> sourceRow = 15;
    }
    item trace_ee10f79be54c1c44 : TraceRecord {
        attribute :>> elementId = "DEF::3800";
        attribute :>> sourceFile = "Rail_MBSE_Function_Interface_v1_final.xlsx";
        attribute :>> sourceSheet = "Product_Hierarchy";
        attribute :>> sourceRow = 16;
    }
    item trace_a969a0a3ac08e429 : TraceRecord {
        attribute :>> elementId = "USAGE::3800";
        attribute :>> sourceFile = "Rail_MBSE_Function_Interface_v1_final.xlsx";
        attribute :>> sourceSheet = "Product_Hierarchy";
        attribute :>> sourceRow = 16;
    }
    item trace_d2b5d1926a65da5e : TraceRecord {
        attribute :>> elementId = "DEF::4100";
        attribute :>> sourceFile = "Rail_MBSE_Function_Interface_v1_final.xlsx";
        attribute :>> sourceSheet = "Product_Hierarchy";
        attribute :>> sourceRow = 17;
    }
    item trace_3f2080cdc091352a : TraceRecord {
        attribute :>> elementId = "USAGE::4100";
        attribute :>> sourceFile = "Rail_MBSE_Function_Interface_v1_final.xlsx";
        attribute :>> sourceSheet = "Product_Hierarchy";
        attribute :>> sourceRow = 17;
    }
    item trace_509bb9315a4c225c : TraceRecord {
        attribute :>> elementId = "DEF::4200";
        attribute :>> sourceFile = "Rail_MBSE_Function_Interface_v1_final.xlsx";
        attribute :>> sourceSheet = "Product_Hierarchy";
        attribute :>> sourceRow = 18;
    }
    item trace_84d09869a6060da6 : TraceRecord {
        attribute :>> elementId = "USAGE::4200";
        attribute :>> sourceFile = "Rail_MBSE_Function_Interface_v1_final.xlsx";
        attribute :>> sourceSheet = "Product_Hierarchy";
        attribute :>> sourceRow = 18;
    }
    item trace_683bb158b0861dce : TraceRecord {
        attribute :>> elementId = "DEF::4400";
        attribute :>> sourceFile = "Rail_MBSE_Function_Interface_v1_final.xlsx";
        attribute :>> sourceSheet = "Product_Hierarchy";
        attribute :>> sourceRow = 19;
    }
    item trace_17e7777e2c674f1c : TraceRecord {
        attribute :>> elementId = "USAGE::4400";
        attribute :>> sourceFile = "Rail_MBSE_Function_Interface_v1_final.xlsx";
        attribute :>> sourceSheet = "Product_Hierarchy";
        attribute :>> sourceRow = 19;
    }
    item trace_23ec15fc877c2b15 : TraceRecord {
        attribute :>> elementId = "DEF::4500";
        attribute :>> sourceFile = "Rail_MBSE_Function_Interface_v1_final.xlsx";
        attribute :>> sourceSheet = "Product_Hierarchy";
        attribute :>> sourceRow = 20;
    }
    item trace_6355284a25a39e36 : TraceRecord {
        attribute :>> elementId = "USAGE::4500";
        attribute :>> sourceFile = "Rail_MBSE_Function_Interface_v1_final.xlsx";
        attribute :>> sourceSheet = "Product_Hierarchy";
        attribute :>> sourceRow = 20;
    }
    item trace_875f98c3c9658727 : TraceRecord {
        attribute :>> elementId = "DEF::5100";
        attribute :>> sourceFile = "Rail_MBSE_Function_Interface_v1_final.xlsx";
        attribute :>> sourceSheet = "Product_Hierarchy";
        attribute :>> sourceRow = 21;
    }
    item trace_de49c10de4aabda1 : TraceRecord {
        attribute :>> elementId = "USAGE::5100";
        attribute :>> sourceFile = "Rail_MBSE_Function_Interface_v1_final.xlsx";
        attribute :>> sourceSheet = "Product_Hierarchy";
        attribute :>> sourceRow = 21;
    }
    item trace_e6d538017c8a1377 : TraceRecord {
        attribute :>> elementId = "DEF::5300";
        attribute :>> sourceFile = "Rail_MBSE_Function_Interface_v1_final.xlsx";
        attribute :>> sourceSheet = "Product_Hierarchy";
        attribute :>> sourceRow = 22;
    }
    item trace_a62eeb0caaa24423 : TraceRecord {
        attribute :>> elementId = "USAGE::5300";
        attribute :>> sourceFile = "Rail_MBSE_Function_Interface_v1_final.xlsx";
        attribute :>> sourceSheet = "Product_Hierarchy";
        attribute :>> sourceRow = 22;
    }
    item trace_fb390eac5a30bc56 : TraceRecord {
        attribute :>> elementId = "DEF::7100";
        attribute :>> sourceFile = "Rail_MBSE_Function_Interface_v1_final.xlsx";
        attribute :>> sourceSheet = "Product_Hierarchy";
        attribute :>> sourceRow = 23;
    }
    item trace_6e382037896e922d : TraceRecord {
        attribute :>> elementId = "USAGE::7100";
        attribute :>> sourceFile = "Rail_MBSE_Function_Interface_v1_final.xlsx";
        attribute :>> sourceSheet = "Product_Hierarchy";
        attribute :>> sourceRow = 23;
    }
    item trace_9e0afe4f79ba01fa : TraceRecord {
        attribute :>> elementId = "DEF::7200";
        attribute :>> sourceFile = "Rail_MBSE_Function_Interface_v1_final.xlsx";
        attribute :>> sourceSheet = "Product_Hierarchy";
        attribute :>> sourceRow = 24;
    }
    item trace_20648d96983d7d42 : TraceRecord {
        attribute :>> elementId = "USAGE::7200";
        attribute :>> sourceFile = "Rail_MBSE_Function_Interface_v1_final.xlsx";
        attribute :>> sourceSheet = "Product_Hierarchy";
        attribute :>> sourceRow = 24;
    }
    item trace_f930564879decb78 : TraceRecord {
        attribute :>> elementId = "DEF::8100";
        attribute :>> sourceFile = "Rail_MBSE_Function_Interface_v1_final.xlsx";
        attribute :>> sourceSheet = "Product_Hierarchy";
        attribute :>> sourceRow = 25;
    }
    item trace_1c244163036d62a2 : TraceRecord {
        attribute :>> elementId = "USAGE::8100";
        attribute :>> sourceFile = "Rail_MBSE_Function_Interface_v1_final.xlsx";
        attribute :>> sourceSheet = "Product_Hierarchy";
        attribute :>> sourceRow = 25;
    }
    item trace_3b91d9ec64950346 : TraceRecord {
        attribute :>> elementId = "DEF::D100";
        attribute :>> sourceFile = "Rail_MBSE_Function_Interface_v1_final.xlsx";
        attribute :>> sourceSheet = "Product_Hierarchy";
        attribute :>> sourceRow = 26;
    }
    item trace_5f9d01324bd3d958 : TraceRecord {
        attribute :>> elementId = "USAGE::D100";
        attribute :>> sourceFile = "Rail_MBSE_Function_Interface_v1_final.xlsx";
        attribute :>> sourceSheet = "Product_Hierarchy";
        attribute :>> sourceRow = 26;
    }
    item trace_c8b32d126d6497c6 : TraceRecord {
        attribute :>> elementId = "DEF::E100";
        attribute :>> sourceFile = "Rail_MBSE_Function_Interface_v1_final.xlsx";
        attribute :>> sourceSheet = "Product_Hierarchy";
        attribute :>> sourceRow = 27;
    }
    item trace_606836ec473165c0 : TraceRecord {
        attribute :>> elementId = "USAGE::E100";
        attribute :>> sourceFile = "Rail_MBSE_Function_Interface_v1_final.xlsx";
        attribute :>> sourceSheet = "Product_Hierarchy";
        attribute :>> sourceRow = 27;
    }
    item trace_40a90b2b0bdb8fd4 : TraceRecord {
        attribute :>> elementId = "DEF::X100";
        attribute :>> sourceFile = "Rail_MBSE_Function_Interface_v1_final.xlsx";
        attribute :>> sourceSheet = "Product_Hierarchy";
        attribute :>> sourceRow = 28;
    }
    item trace_7cca3242f1e159c9 : TraceRecord {
        attribute :>> elementId = "USAGE::X100";
        attribute :>> sourceFile = "Rail_MBSE_Function_Interface_v1_final.xlsx";
        attribute :>> sourceSheet = "Product_Hierarchy";
        attribute :>> sourceRow = 28;
    }
    item trace_a40fa5225a93a3d3 : TraceRecord {
        attribute :>> elementId = "DEF::3110";
        attribute :>> sourceFile = "Rail_MBSE_Function_Interface_v1_final.xlsx";
        attribute :>> sourceSheet = "Product_Hierarchy";
        attribute :>> sourceRow = 29;
    }
    item trace_3ea2105a8b1a0261 : TraceRecord {
        attribute :>> elementId = "USAGE::3110";
        attribute :>> sourceFile = "Rail_MBSE_Function_Interface_v1_final.xlsx";
        attribute :>> sourceSheet = "Product_Hierarchy";
        attribute :>> sourceRow = 29;
    }
    item trace_3d4d046dda2f3ecc : TraceRecord {
        attribute :>> elementId = "DEF::3120";
        attribute :>> sourceFile = "Rail_MBSE_Function_Interface_v1_final.xlsx";
        attribute :>> sourceSheet = "Product_Hierarchy";
        attribute :>> sourceRow = 30;
    }
    item trace_c498d6dc174a22cf : TraceRecord {
        attribute :>> elementId = "USAGE::3120";
        attribute :>> sourceFile = "Rail_MBSE_Function_Interface_v1_final.xlsx";
        attribute :>> sourceSheet = "Product_Hierarchy";
        attribute :>> sourceRow = 30;
    }
    item trace_e1557751cfa52e40 : TraceRecord {
        attribute :>> elementId = "DEF::3130";
        attribute :>> sourceFile = "Rail_MBSE_Function_Interface_v1_final.xlsx";
        attribute :>> sourceSheet = "Product_Hierarchy";
        attribute :>> sourceRow = 31;
    }
    item trace_5f3b1b0935b5d295 : TraceRecord {
        attribute :>> elementId = "USAGE::3130";
        attribute :>> sourceFile = "Rail_MBSE_Function_Interface_v1_final.xlsx";
        attribute :>> sourceSheet = "Product_Hierarchy";
        attribute :>> sourceRow = 31;
    }
    item trace_1153af3ffaa1c570 : TraceRecord {
        attribute :>> elementId = "DEF::3510";
        attribute :>> sourceFile = "Rail_MBSE_Function_Interface_v1_final.xlsx";
        attribute :>> sourceSheet = "Product_Hierarchy";
        attribute :>> sourceRow = 32;
    }
    item trace_db0c0d6857bd6761 : TraceRecord {
        attribute :>> elementId = "USAGE::3510";
        attribute :>> sourceFile = "Rail_MBSE_Function_Interface_v1_final.xlsx";
        attribute :>> sourceSheet = "Product_Hierarchy";
        attribute :>> sourceRow = 32;
    }
    item trace_9ee18d458a9aa888 : TraceRecord {
        attribute :>> elementId = "DEF::3640";
        attribute :>> sourceFile = "Rail_MBSE_Function_Interface_v1_final.xlsx";
        attribute :>> sourceSheet = "Product_Hierarchy";
        attribute :>> sourceRow = 33;
    }
    item trace_3949cb351e2c4135 : TraceRecord {
        attribute :>> elementId = "USAGE::3640";
        attribute :>> sourceFile = "Rail_MBSE_Function_Interface_v1_final.xlsx";
        attribute :>> sourceSheet = "Product_Hierarchy";
        attribute :>> sourceRow = 33;
    }
    item trace_b1bd8e33b7c6b128 : TraceRecord {
        attribute :>> elementId = "DEF::3810";
        attribute :>> sourceFile = "Rail_MBSE_Function_Interface_v1_final.xlsx";
        attribute :>> sourceSheet = "Product_Hierarchy";
        attribute :>> sourceRow = 34;
    }
    item trace_c13aabb543daf571 : TraceRecord {
        attribute :>> elementId = "USAGE::3810";
        attribute :>> sourceFile = "Rail_MBSE_Function_Interface_v1_final.xlsx";
        attribute :>> sourceSheet = "Product_Hierarchy";
        attribute :>> sourceRow = 34;
    }
    item trace_08bd1c33839b94b5 : TraceRecord {
        attribute :>> elementId = "DEF::4110";
        attribute :>> sourceFile = "Rail_MBSE_Function_Interface_v1_final.xlsx";
        attribute :>> sourceSheet = "Product_Hierarchy";
        attribute :>> sourceRow = 35;
    }
    item trace_e846f4a01f9e0791 : TraceRecord {
        attribute :>> elementId = "USAGE::4110";
        attribute :>> sourceFile = "Rail_MBSE_Function_Interface_v1_final.xlsx";
        attribute :>> sourceSheet = "Product_Hierarchy";
        attribute :>> sourceRow = 35;
    }
    item trace_dda0c52618064d60 : TraceRecord {
        attribute :>> elementId = "DEF::4120";
        attribute :>> sourceFile = "Rail_MBSE_Function_Interface_v1_final.xlsx";
        attribute :>> sourceSheet = "Product_Hierarchy";
        attribute :>> sourceRow = 36;
    }
    item trace_77d84a815bf31ff4 : TraceRecord {
        attribute :>> elementId = "USAGE::4120";
        attribute :>> sourceFile = "Rail_MBSE_Function_Interface_v1_final.xlsx";
        attribute :>> sourceSheet = "Product_Hierarchy";
        attribute :>> sourceRow = 36;
    }
    item trace_dc0b75951990a323 : TraceRecord {
        attribute :>> elementId = "DEF::4210";
        attribute :>> sourceFile = "Rail_MBSE_Function_Interface_v1_final.xlsx";
        attribute :>> sourceSheet = "Product_Hierarchy";
        attribute :>> sourceRow = 37;
    }
    item trace_58a190c38d65f112 : TraceRecord {
        attribute :>> elementId = "USAGE::4210";
        attribute :>> sourceFile = "Rail_MBSE_Function_Interface_v1_final.xlsx";
        attribute :>> sourceSheet = "Product_Hierarchy";
        attribute :>> sourceRow = 37;
    }
    item trace_eb0473ff81344904 : TraceRecord {
        attribute :>> elementId = "DEF::4230";
        attribute :>> sourceFile = "Rail_MBSE_Function_Interface_v1_final.xlsx";
        attribute :>> sourceSheet = "Product_Hierarchy";
        attribute :>> sourceRow = 38;
    }
    item trace_a70ee62f7305272d : TraceRecord {
        attribute :>> elementId = "USAGE::4230";
        attribute :>> sourceFile = "Rail_MBSE_Function_Interface_v1_final.xlsx";
        attribute :>> sourceSheet = "Product_Hierarchy";
        attribute :>> sourceRow = 38;
    }
    item trace_c322974250d51060 : TraceRecord {
        attribute :>> elementId = "DEF::4240";
        attribute :>> sourceFile = "Rail_MBSE_Function_Interface_v1_final.xlsx";
        attribute :>> sourceSheet = "Product_Hierarchy";
        attribute :>> sourceRow = 39;
    }
    item trace_9382a52f25b03a9f : TraceRecord {
        attribute :>> elementId = "USAGE::4240";
        attribute :>> sourceFile = "Rail_MBSE_Function_Interface_v1_final.xlsx";
        attribute :>> sourceSheet = "Product_Hierarchy";
        attribute :>> sourceRow = 39;
    }
    item trace_18bdf8169097762a : TraceRecord {
        attribute :>> elementId = "DEF::4410";
        attribute :>> sourceFile = "Rail_MBSE_Function_Interface_v1_final.xlsx";
        attribute :>> sourceSheet = "Product_Hierarchy";
        attribute :>> sourceRow = 40;
    }
    item trace_a51be427c765e492 : TraceRecord {
        attribute :>> elementId = "USAGE::4410";
        attribute :>> sourceFile = "Rail_MBSE_Function_Interface_v1_final.xlsx";
        attribute :>> sourceSheet = "Product_Hierarchy";
        attribute :>> sourceRow = 40;
    }
    item trace_69b337d67ed1822d : TraceRecord {
        attribute :>> elementId = "DEF::4510";
        attribute :>> sourceFile = "Rail_MBSE_Function_Interface_v1_final.xlsx";
        attribute :>> sourceSheet = "Product_Hierarchy";
        attribute :>> sourceRow = 41;
    }
    item trace_30e137b706259a6c : TraceRecord {
        attribute :>> elementId = "USAGE::4510";
        attribute :>> sourceFile = "Rail_MBSE_Function_Interface_v1_final.xlsx";
        attribute :>> sourceSheet = "Product_Hierarchy";
        attribute :>> sourceRow = 41;
    }
    item trace_c287436e42cda00c : TraceRecord {
        attribute :>> elementId = "DEF::5110";
        attribute :>> sourceFile = "Rail_MBSE_Function_Interface_v1_final.xlsx";
        attribute :>> sourceSheet = "Product_Hierarchy";
        attribute :>> sourceRow = 42;
    }
    item trace_4cdcf952c398d532 : TraceRecord {
        attribute :>> elementId = "USAGE::5110";
        attribute :>> sourceFile = "Rail_MBSE_Function_Interface_v1_final.xlsx";
        attribute :>> sourceSheet = "Product_Hierarchy";
        attribute :>> sourceRow = 42;
    }
    item trace_3468ad3641840835 : TraceRecord {
        attribute :>> elementId = "DEF::5120";
        attribute :>> sourceFile = "Rail_MBSE_Function_Interface_v1_final.xlsx";
        attribute :>> sourceSheet = "Product_Hierarchy";
        attribute :>> sourceRow = 43;
    }
    item trace_d95bb4b8b36f02ee : TraceRecord {
        attribute :>> elementId = "USAGE::5120";
        attribute :>> sourceFile = "Rail_MBSE_Function_Interface_v1_final.xlsx";
        attribute :>> sourceSheet = "Product_Hierarchy";
        attribute :>> sourceRow = 43;
    }
    item trace_4921ce88bd0f08f3 : TraceRecord {
        attribute :>> elementId = "DEF::5130";
        attribute :>> sourceFile = "Rail_MBSE_Function_Interface_v1_final.xlsx";
        attribute :>> sourceSheet = "Product_Hierarchy";
        attribute :>> sourceRow = 44;
    }
    item trace_a81260b7863f8935 : TraceRecord {
        attribute :>> elementId = "USAGE::5130";
        attribute :>> sourceFile = "Rail_MBSE_Function_Interface_v1_final.xlsx";
        attribute :>> sourceSheet = "Product_Hierarchy";
        attribute :>> sourceRow = 44;
    }
    item trace_21d17acabc7a6ff1 : TraceRecord {
        attribute :>> elementId = "DEF::5140";
        attribute :>> sourceFile = "Rail_MBSE_Function_Interface_v1_final.xlsx";
        attribute :>> sourceSheet = "Product_Hierarchy";
        attribute :>> sourceRow = 45;
    }
    item trace_95a26027ec7f505b : TraceRecord {
        attribute :>> elementId = "USAGE::5140";
        attribute :>> sourceFile = "Rail_MBSE_Function_Interface_v1_final.xlsx";
        attribute :>> sourceSheet = "Product_Hierarchy";
        attribute :>> sourceRow = 45;
    }
    item trace_fa0955aa15db95de : TraceRecord {
        attribute :>> elementId = "DEF::5310";
        attribute :>> sourceFile = "Rail_MBSE_Function_Interface_v1_final.xlsx";
        attribute :>> sourceSheet = "Product_Hierarchy";
        attribute :>> sourceRow = 46;
    }
    item trace_04f3f5d242dc1d9e : TraceRecord {
        attribute :>> elementId = "USAGE::5310";
        attribute :>> sourceFile = "Rail_MBSE_Function_Interface_v1_final.xlsx";
        attribute :>> sourceSheet = "Product_Hierarchy";
        attribute :>> sourceRow = 46;
    }
    item trace_46683d29d44a4fb2 : TraceRecord {
        attribute :>> elementId = "DEF::7120";
        attribute :>> sourceFile = "Rail_MBSE_Function_Interface_v1_final.xlsx";
        attribute :>> sourceSheet = "Product_Hierarchy";
        attribute :>> sourceRow = 47;
    }
    item trace_68a3f8ec54f5361b : TraceRecord {
        attribute :>> elementId = "USAGE::7120";
        attribute :>> sourceFile = "Rail_MBSE_Function_Interface_v1_final.xlsx";
        attribute :>> sourceSheet = "Product_Hierarchy";
        attribute :>> sourceRow = 47;
    }
    item trace_58b2c07e029177ec : TraceRecord {
        attribute :>> elementId = "DEF::7130";
        attribute :>> sourceFile = "Rail_MBSE_Function_Interface_v1_final.xlsx";
        attribute :>> sourceSheet = "Product_Hierarchy";
        attribute :>> sourceRow = 48;
    }
    item trace_daba9eb8cc7b68aa : TraceRecord {
        attribute :>> elementId = "USAGE::7130";
        attribute :>> sourceFile = "Rail_MBSE_Function_Interface_v1_final.xlsx";
        attribute :>> sourceSheet = "Product_Hierarchy";
        attribute :>> sourceRow = 48;
    }
    item trace_18addc0092bd2601 : TraceRecord {
        attribute :>> elementId = "DEF::7140";
        attribute :>> sourceFile = "Rail_MBSE_Function_Interface_v1_final.xlsx";
        attribute :>> sourceSheet = "Product_Hierarchy";
        attribute :>> sourceRow = 49;
    }
    item trace_326b71cb1088cb88 : TraceRecord {
        attribute :>> elementId = "USAGE::7140";
        attribute :>> sourceFile = "Rail_MBSE_Function_Interface_v1_final.xlsx";
        attribute :>> sourceSheet = "Product_Hierarchy";
        attribute :>> sourceRow = 49;
    }
    item trace_50a7fe4107888210 : TraceRecord {
        attribute :>> elementId = "DEF::7210";
        attribute :>> sourceFile = "Rail_MBSE_Function_Interface_v1_final.xlsx";
        attribute :>> sourceSheet = "Product_Hierarchy";
        attribute :>> sourceRow = 50;
    }
    item trace_5e818f5ec4c1527e : TraceRecord {
        attribute :>> elementId = "USAGE::7210";
        attribute :>> sourceFile = "Rail_MBSE_Function_Interface_v1_final.xlsx";
        attribute :>> sourceSheet = "Product_Hierarchy";
        attribute :>> sourceRow = 50;
    }
    item trace_9a4d7c75aa9219e6 : TraceRecord {
        attribute :>> elementId = "DEF::7220";
        attribute :>> sourceFile = "Rail_MBSE_Function_Interface_v1_final.xlsx";
        attribute :>> sourceSheet = "Product_Hierarchy";
        attribute :>> sourceRow = 51;
    }
    item trace_064a1e74edfa4997 : TraceRecord {
        attribute :>> elementId = "USAGE::7220";
        attribute :>> sourceFile = "Rail_MBSE_Function_Interface_v1_final.xlsx";
        attribute :>> sourceSheet = "Product_Hierarchy";
        attribute :>> sourceRow = 51;
    }
    item trace_84b5e740633b083f : TraceRecord {
        attribute :>> elementId = "DEF::7250";
        attribute :>> sourceFile = "Rail_MBSE_Function_Interface_v1_final.xlsx";
        attribute :>> sourceSheet = "Product_Hierarchy";
        attribute :>> sourceRow = 52;
    }
    item trace_8c9587a6a25e5886 : TraceRecord {
        attribute :>> elementId = "USAGE::7250";
        attribute :>> sourceFile = "Rail_MBSE_Function_Interface_v1_final.xlsx";
        attribute :>> sourceSheet = "Product_Hierarchy";
        attribute :>> sourceRow = 52;
    }
    item trace_5d6fbd43707de553 : TraceRecord {
        attribute :>> elementId = "DEF::7280";
        attribute :>> sourceFile = "Rail_MBSE_Function_Interface_v1_final.xlsx";
        attribute :>> sourceSheet = "Product_Hierarchy";
        attribute :>> sourceRow = 53;
    }
    item trace_b0cd11088f2a225d : TraceRecord {
        attribute :>> elementId = "USAGE::7280";
        attribute :>> sourceFile = "Rail_MBSE_Function_Interface_v1_final.xlsx";
        attribute :>> sourceSheet = "Product_Hierarchy";
        attribute :>> sourceRow = 53;
    }
    item trace_cd231c67bc54d1f9 : TraceRecord {
        attribute :>> elementId = "DEF::8120";
        attribute :>> sourceFile = "Rail_MBSE_Function_Interface_v1_final.xlsx";
        attribute :>> sourceSheet = "Product_Hierarchy";
        attribute :>> sourceRow = 54;
    }
    item trace_589b5e72331bcc4c : TraceRecord {
        attribute :>> elementId = "USAGE::8120";
        attribute :>> sourceFile = "Rail_MBSE_Function_Interface_v1_final.xlsx";
        attribute :>> sourceSheet = "Product_Hierarchy";
        attribute :>> sourceRow = 54;
    }
    item trace_36c735a31a77b1e0 : TraceRecord {
        attribute :>> elementId = "DEF::8150";
        attribute :>> sourceFile = "Rail_MBSE_Function_Interface_v1_final.xlsx";
        attribute :>> sourceSheet = "Product_Hierarchy";
        attribute :>> sourceRow = 55;
    }
    item trace_e5c82af18ca986fc : TraceRecord {
        attribute :>> elementId = "USAGE::8150";
        attribute :>> sourceFile = "Rail_MBSE_Function_Interface_v1_final.xlsx";
        attribute :>> sourceSheet = "Product_Hierarchy";
        attribute :>> sourceRow = 55;
    }
    item trace_5d955bff94c6d757 : TraceRecord {
        attribute :>> elementId = "DEF::8160";
        attribute :>> sourceFile = "Rail_MBSE_Function_Interface_v1_final.xlsx";
        attribute :>> sourceSheet = "Product_Hierarchy";
        attribute :>> sourceRow = 56;
    }
    item trace_12b50455365d793b : TraceRecord {
        attribute :>> elementId = "USAGE::8160";
        attribute :>> sourceFile = "Rail_MBSE_Function_Interface_v1_final.xlsx";
        attribute :>> sourceSheet = "Product_Hierarchy";
        attribute :>> sourceRow = 56;
    }
    item trace_ec0b962a351d48a7 : TraceRecord {
        attribute :>> elementId = "DEF::D110";
        attribute :>> sourceFile = "Rail_MBSE_Function_Interface_v1_final.xlsx";
        attribute :>> sourceSheet = "Product_Hierarchy";
        attribute :>> sourceRow = 57;
    }
    item trace_f7d97bec8b4a7511 : TraceRecord {
        attribute :>> elementId = "USAGE::D110";
        attribute :>> sourceFile = "Rail_MBSE_Function_Interface_v1_final.xlsx";
        attribute :>> sourceSheet = "Product_Hierarchy";
        attribute :>> sourceRow = 57;
    }
    item trace_7c3376f7480ee9e9 : TraceRecord {
        attribute :>> elementId = "DEF::D120";
        attribute :>> sourceFile = "Rail_MBSE_Function_Interface_v1_final.xlsx";
        attribute :>> sourceSheet = "Product_Hierarchy";
        attribute :>> sourceRow = 58;
    }
    item trace_8c7a7fe5158bea8f : TraceRecord {
        attribute :>> elementId = "USAGE::D120";
        attribute :>> sourceFile = "Rail_MBSE_Function_Interface_v1_final.xlsx";
        attribute :>> sourceSheet = "Product_Hierarchy";
        attribute :>> sourceRow = 58;
    }
    item trace_d7fe47122b359adc : TraceRecord {
        attribute :>> elementId = "DEF::D130";
        attribute :>> sourceFile = "Rail_MBSE_Function_Interface_v1_final.xlsx";
        attribute :>> sourceSheet = "Product_Hierarchy";
        attribute :>> sourceRow = 59;
    }
    item trace_fd2e506555bda3e0 : TraceRecord {
        attribute :>> elementId = "USAGE::D130";
        attribute :>> sourceFile = "Rail_MBSE_Function_Interface_v1_final.xlsx";
        attribute :>> sourceSheet = "Product_Hierarchy";
        attribute :>> sourceRow = 59;
    }
    item trace_0eaccd0af95ec3bb : TraceRecord {
        attribute :>> elementId = "DEF::X110";
        attribute :>> sourceFile = "Rail_MBSE_Function_Interface_v1_final.xlsx";
        attribute :>> sourceSheet = "Product_Hierarchy";
        attribute :>> sourceRow = 60;
    }
    item trace_9ded7f916617f1fe : TraceRecord {
        attribute :>> elementId = "USAGE::X110";
        attribute :>> sourceFile = "Rail_MBSE_Function_Interface_v1_final.xlsx";
        attribute :>> sourceSheet = "Product_Hierarchy";
        attribute :>> sourceRow = 60;
    }
    item trace_30813b8f376adcc3 : TraceRecord {
        attribute :>> elementId = "DEF::X120";
        attribute :>> sourceFile = "Rail_MBSE_Function_Interface_v1_final.xlsx";
        attribute :>> sourceSheet = "Product_Hierarchy";
        attribute :>> sourceRow = 61;
    }
    item trace_11e2d23c3890f4d1 : TraceRecord {
        attribute :>> elementId = "USAGE::X120";
        attribute :>> sourceFile = "Rail_MBSE_Function_Interface_v1_final.xlsx";
        attribute :>> sourceSheet = "Product_Hierarchy";
        attribute :>> sourceRow = 61;
    }
    item trace_da4f0ad027231705 : TraceRecord {
        attribute :>> elementId = "DEF::X130";
        attribute :>> sourceFile = "Rail_MBSE_Function_Interface_v1_final.xlsx";
        attribute :>> sourceSheet = "Product_Hierarchy";
        attribute :>> sourceRow = 62;
    }
    item trace_e774b4db6f8c1824 : TraceRecord {
        attribute :>> elementId = "USAGE::X130";
        attribute :>> sourceFile = "Rail_MBSE_Function_Interface_v1_final.xlsx";
        attribute :>> sourceSheet = "Product_Hierarchy";
        attribute :>> sourceRow = 62;
    }
    item trace_fe2c74d7ab8f02d5 : TraceRecord {
        attribute :>> elementId = "DEF::3111";
        attribute :>> sourceFile = "Rail_MBSE_Function_Interface_v1_final.xlsx";
        attribute :>> sourceSheet = "Product_Hierarchy";
        attribute :>> sourceRow = 63;
    }
    item trace_94bb77d4d5f1cabf : TraceRecord {
        attribute :>> elementId = "USAGE::3111";
        attribute :>> sourceFile = "Rail_MBSE_Function_Interface_v1_final.xlsx";
        attribute :>> sourceSheet = "Product_Hierarchy";
        attribute :>> sourceRow = 63;
    }
    item trace_1c4da025cb33cb96 : TraceRecord {
        attribute :>> elementId = "DEF::3112";
        attribute :>> sourceFile = "Rail_MBSE_Function_Interface_v1_final.xlsx";
        attribute :>> sourceSheet = "Product_Hierarchy";
        attribute :>> sourceRow = 64;
    }
    item trace_440abd8f64cdb671 : TraceRecord {
        attribute :>> elementId = "USAGE::3112";
        attribute :>> sourceFile = "Rail_MBSE_Function_Interface_v1_final.xlsx";
        attribute :>> sourceSheet = "Product_Hierarchy";
        attribute :>> sourceRow = 64;
    }
    item trace_155d9a33859785d8 : TraceRecord {
        attribute :>> elementId = "DEF::3121";
        attribute :>> sourceFile = "Rail_MBSE_Function_Interface_v1_final.xlsx";
        attribute :>> sourceSheet = "Product_Hierarchy";
        attribute :>> sourceRow = 65;
    }
    item trace_4979636f6c936d11 : TraceRecord {
        attribute :>> elementId = "USAGE::3121";
        attribute :>> sourceFile = "Rail_MBSE_Function_Interface_v1_final.xlsx";
        attribute :>> sourceSheet = "Product_Hierarchy";
        attribute :>> sourceRow = 65;
    }
    item trace_a4cb85d203124600 : TraceRecord {
        attribute :>> elementId = "DEF::3131";
        attribute :>> sourceFile = "Rail_MBSE_Function_Interface_v1_final.xlsx";
        attribute :>> sourceSheet = "Product_Hierarchy";
        attribute :>> sourceRow = 66;
    }
    item trace_306bf4dd5200d751 : TraceRecord {
        attribute :>> elementId = "USAGE::3131";
        attribute :>> sourceFile = "Rail_MBSE_Function_Interface_v1_final.xlsx";
        attribute :>> sourceSheet = "Product_Hierarchy";
        attribute :>> sourceRow = 66;
    }
    item trace_956f6d7c96e7bede : TraceRecord {
        attribute :>> elementId = "DEF::3132";
        attribute :>> sourceFile = "Rail_MBSE_Function_Interface_v1_final.xlsx";
        attribute :>> sourceSheet = "Product_Hierarchy";
        attribute :>> sourceRow = 67;
    }
    item trace_25ceac426896bbab : TraceRecord {
        attribute :>> elementId = "USAGE::3132";
        attribute :>> sourceFile = "Rail_MBSE_Function_Interface_v1_final.xlsx";
        attribute :>> sourceSheet = "Product_Hierarchy";
        attribute :>> sourceRow = 67;
    }
    item trace_af3e34f38d5458da : TraceRecord {
        attribute :>> elementId = "DEF::3133";
        attribute :>> sourceFile = "Rail_MBSE_Function_Interface_v1_final.xlsx";
        attribute :>> sourceSheet = "Product_Hierarchy";
        attribute :>> sourceRow = 68;
    }
    item trace_b725394c07642b5b : TraceRecord {
        attribute :>> elementId = "USAGE::3133";
        attribute :>> sourceFile = "Rail_MBSE_Function_Interface_v1_final.xlsx";
        attribute :>> sourceSheet = "Product_Hierarchy";
        attribute :>> sourceRow = 68;
    }
    item trace_63fd0df0714e20ed : TraceRecord {
        attribute :>> elementId = "DEF::3511";
        attribute :>> sourceFile = "Rail_MBSE_Function_Interface_v1_final.xlsx";
        attribute :>> sourceSheet = "Product_Hierarchy";
        attribute :>> sourceRow = 69;
    }
    item trace_00471370524bc146 : TraceRecord {
        attribute :>> elementId = "USAGE::3511";
        attribute :>> sourceFile = "Rail_MBSE_Function_Interface_v1_final.xlsx";
        attribute :>> sourceSheet = "Product_Hierarchy";
        attribute :>> sourceRow = 69;
    }
    item trace_815b1aea60b1d3dd : TraceRecord {
        attribute :>> elementId = "DEF::3512";
        attribute :>> sourceFile = "Rail_MBSE_Function_Interface_v1_final.xlsx";
        attribute :>> sourceSheet = "Product_Hierarchy";
        attribute :>> sourceRow = 70;
    }
    item trace_c1ea2a4d4acbc320 : TraceRecord {
        attribute :>> elementId = "USAGE::3512";
        attribute :>> sourceFile = "Rail_MBSE_Function_Interface_v1_final.xlsx";
        attribute :>> sourceSheet = "Product_Hierarchy";
        attribute :>> sourceRow = 70;
    }
    item trace_49043e6c1421bb7d : TraceRecord {
        attribute :>> elementId = "DEF::3514";
        attribute :>> sourceFile = "Rail_MBSE_Function_Interface_v1_final.xlsx";
        attribute :>> sourceSheet = "Product_Hierarchy";
        attribute :>> sourceRow = 71;
    }
    item trace_5126dc7f4b22223c : TraceRecord {
        attribute :>> elementId = "USAGE::3514";
        attribute :>> sourceFile = "Rail_MBSE_Function_Interface_v1_final.xlsx";
        attribute :>> sourceSheet = "Product_Hierarchy";
        attribute :>> sourceRow = 71;
    }
    item trace_fc9cb731af1b8254 : TraceRecord {
        attribute :>> elementId = "DEF::3641";
        attribute :>> sourceFile = "Rail_MBSE_Function_Interface_v1_final.xlsx";
        attribute :>> sourceSheet = "Product_Hierarchy";
        attribute :>> sourceRow = 72;
    }
    item trace_96f732a4ec740fe8 : TraceRecord {
        attribute :>> elementId = "USAGE::3641";
        attribute :>> sourceFile = "Rail_MBSE_Function_Interface_v1_final.xlsx";
        attribute :>> sourceSheet = "Product_Hierarchy";
        attribute :>> sourceRow = 72;
    }
    item trace_cacc9f51a25752f5 : TraceRecord {
        attribute :>> elementId = "DEF::3643";
        attribute :>> sourceFile = "Rail_MBSE_Function_Interface_v1_final.xlsx";
        attribute :>> sourceSheet = "Product_Hierarchy";
        attribute :>> sourceRow = 73;
    }
    item trace_00d65530b10d1075 : TraceRecord {
        attribute :>> elementId = "USAGE::3643";
        attribute :>> sourceFile = "Rail_MBSE_Function_Interface_v1_final.xlsx";
        attribute :>> sourceSheet = "Product_Hierarchy";
        attribute :>> sourceRow = 73;
    }
    item trace_2f575a45f6e8db64 : TraceRecord {
        attribute :>> elementId = "DEF::3644";
        attribute :>> sourceFile = "Rail_MBSE_Function_Interface_v1_final.xlsx";
        attribute :>> sourceSheet = "Product_Hierarchy";
        attribute :>> sourceRow = 74;
    }
    item trace_08d17e912fca9dd6 : TraceRecord {
        attribute :>> elementId = "USAGE::3644";
        attribute :>> sourceFile = "Rail_MBSE_Function_Interface_v1_final.xlsx";
        attribute :>> sourceSheet = "Product_Hierarchy";
        attribute :>> sourceRow = 74;
    }
    item trace_baba3b57399a8a94 : TraceRecord {
        attribute :>> elementId = "DEF::3811";
        attribute :>> sourceFile = "Rail_MBSE_Function_Interface_v1_final.xlsx";
        attribute :>> sourceSheet = "Product_Hierarchy";
        attribute :>> sourceRow = 75;
    }
    item trace_629ae6f1bbd45d4f : TraceRecord {
        attribute :>> elementId = "USAGE::3811";
        attribute :>> sourceFile = "Rail_MBSE_Function_Interface_v1_final.xlsx";
        attribute :>> sourceSheet = "Product_Hierarchy";
        attribute :>> sourceRow = 75;
    }
    item trace_40abf0a102bdc7f0 : TraceRecord {
        attribute :>> elementId = "DEF::3813";
        attribute :>> sourceFile = "Rail_MBSE_Function_Interface_v1_final.xlsx";
        attribute :>> sourceSheet = "Product_Hierarchy";
        attribute :>> sourceRow = 76;
    }
    item trace_df88e2a5af75b7a8 : TraceRecord {
        attribute :>> elementId = "USAGE::3813";
        attribute :>> sourceFile = "Rail_MBSE_Function_Interface_v1_final.xlsx";
        attribute :>> sourceSheet = "Product_Hierarchy";
        attribute :>> sourceRow = 76;
    }
    item trace_10512113789685a4 : TraceRecord {
        attribute :>> elementId = "DEF::3814";
        attribute :>> sourceFile = "Rail_MBSE_Function_Interface_v1_final.xlsx";
        attribute :>> sourceSheet = "Product_Hierarchy";
        attribute :>> sourceRow = 77;
    }
    item trace_415a5d09ae4085bf : TraceRecord {
        attribute :>> elementId = "USAGE::3814";
        attribute :>> sourceFile = "Rail_MBSE_Function_Interface_v1_final.xlsx";
        attribute :>> sourceSheet = "Product_Hierarchy";
        attribute :>> sourceRow = 77;
    }
    item trace_51a71967531309c1 : TraceRecord {
        attribute :>> elementId = "DEF::4111";
        attribute :>> sourceFile = "Rail_MBSE_Function_Interface_v1_final.xlsx";
        attribute :>> sourceSheet = "Product_Hierarchy";
        attribute :>> sourceRow = 78;
    }
    item trace_325cd01d70fb6b95 : TraceRecord {
        attribute :>> elementId = "USAGE::4111";
        attribute :>> sourceFile = "Rail_MBSE_Function_Interface_v1_final.xlsx";
        attribute :>> sourceSheet = "Product_Hierarchy";
        attribute :>> sourceRow = 78;
    }
    item trace_e8231fbf64acfbb2 : TraceRecord {
        attribute :>> elementId = "DEF::411C";
        attribute :>> sourceFile = "Rail_MBSE_Function_Interface_v1_final.xlsx";
        attribute :>> sourceSheet = "Product_Hierarchy";
        attribute :>> sourceRow = 79;
    }
    item trace_9c230d0b0f9ff5f4 : TraceRecord {
        attribute :>> elementId = "USAGE::411C";
        attribute :>> sourceFile = "Rail_MBSE_Function_Interface_v1_final.xlsx";
        attribute :>> sourceSheet = "Product_Hierarchy";
        attribute :>> sourceRow = 79;
    }
    item trace_a2a3b21c459d8b5e : TraceRecord {
        attribute :>> elementId = "DEF::4121";
        attribute :>> sourceFile = "Rail_MBSE_Function_Interface_v1_final.xlsx";
        attribute :>> sourceSheet = "Product_Hierarchy";
        attribute :>> sourceRow = 80;
    }
    item trace_7a85c751137ce1f9 : TraceRecord {
        attribute :>> elementId = "USAGE::4121";
        attribute :>> sourceFile = "Rail_MBSE_Function_Interface_v1_final.xlsx";
        attribute :>> sourceSheet = "Product_Hierarchy";
        attribute :>> sourceRow = 80;
    }
    item trace_a5fdd829a456df74 : TraceRecord {
        attribute :>> elementId = "DEF::4211";
        attribute :>> sourceFile = "Rail_MBSE_Function_Interface_v1_final.xlsx";
        attribute :>> sourceSheet = "Product_Hierarchy";
        attribute :>> sourceRow = 81;
    }
    item trace_cdbb03d8fcd72ba5 : TraceRecord {
        attribute :>> elementId = "USAGE::4211";
        attribute :>> sourceFile = "Rail_MBSE_Function_Interface_v1_final.xlsx";
        attribute :>> sourceSheet = "Product_Hierarchy";
        attribute :>> sourceRow = 81;
    }
    item trace_a0292d4d2448f60b : TraceRecord {
        attribute :>> elementId = "DEF::4212";
        attribute :>> sourceFile = "Rail_MBSE_Function_Interface_v1_final.xlsx";
        attribute :>> sourceSheet = "Product_Hierarchy";
        attribute :>> sourceRow = 82;
    }
    item trace_7989863bb0e6fe30 : TraceRecord {
        attribute :>> elementId = "USAGE::4212";
        attribute :>> sourceFile = "Rail_MBSE_Function_Interface_v1_final.xlsx";
        attribute :>> sourceSheet = "Product_Hierarchy";
        attribute :>> sourceRow = 82;
    }
    item trace_1447e5ca3461f7ab : TraceRecord {
        attribute :>> elementId = "DEF::4235";
        attribute :>> sourceFile = "Rail_MBSE_Function_Interface_v1_final.xlsx";
        attribute :>> sourceSheet = "Product_Hierarchy";
        attribute :>> sourceRow = 83;
    }
    item trace_4c6608291d08377d : TraceRecord {
        attribute :>> elementId = "USAGE::4235";
        attribute :>> sourceFile = "Rail_MBSE_Function_Interface_v1_final.xlsx";
        attribute :>> sourceSheet = "Product_Hierarchy";
        attribute :>> sourceRow = 83;
    }
    item trace_3132b1625ef14bf1 : TraceRecord {
        attribute :>> elementId = "DEF::4236";
        attribute :>> sourceFile = "Rail_MBSE_Function_Interface_v1_final.xlsx";
        attribute :>> sourceSheet = "Product_Hierarchy";
        attribute :>> sourceRow = 84;
    }
    item trace_0056d6417622719e : TraceRecord {
        attribute :>> elementId = "USAGE::4236";
        attribute :>> sourceFile = "Rail_MBSE_Function_Interface_v1_final.xlsx";
        attribute :>> sourceSheet = "Product_Hierarchy";
        attribute :>> sourceRow = 84;
    }
    item trace_add023323fd739e2 : TraceRecord {
        attribute :>> elementId = "DEF::4238";
        attribute :>> sourceFile = "Rail_MBSE_Function_Interface_v1_final.xlsx";
        attribute :>> sourceSheet = "Product_Hierarchy";
        attribute :>> sourceRow = 85;
    }
    item trace_5980bc3d954d679c : TraceRecord {
        attribute :>> elementId = "USAGE::4238";
        attribute :>> sourceFile = "Rail_MBSE_Function_Interface_v1_final.xlsx";
        attribute :>> sourceSheet = "Product_Hierarchy";
        attribute :>> sourceRow = 85;
    }
    item trace_cbf711f1908942b5 : TraceRecord {
        attribute :>> elementId = "DEF::4239";
        attribute :>> sourceFile = "Rail_MBSE_Function_Interface_v1_final.xlsx";
        attribute :>> sourceSheet = "Product_Hierarchy";
        attribute :>> sourceRow = 86;
    }
    item trace_b56abefcf6b2d9c9 : TraceRecord {
        attribute :>> elementId = "USAGE::4239";
        attribute :>> sourceFile = "Rail_MBSE_Function_Interface_v1_final.xlsx";
        attribute :>> sourceSheet = "Product_Hierarchy";
        attribute :>> sourceRow = 86;
    }
    item trace_84b2b6ea8034bdf0 : TraceRecord {
        attribute :>> elementId = "DEF::4241";
        attribute :>> sourceFile = "Rail_MBSE_Function_Interface_v1_final.xlsx";
        attribute :>> sourceSheet = "Product_Hierarchy";
        attribute :>> sourceRow = 87;
    }
    item trace_e7b06f690322f44f : TraceRecord {
        attribute :>> elementId = "USAGE::4241";
        attribute :>> sourceFile = "Rail_MBSE_Function_Interface_v1_final.xlsx";
        attribute :>> sourceSheet = "Product_Hierarchy";
        attribute :>> sourceRow = 87;
    }
    item trace_a28895ddc3c17c6d : TraceRecord {
        attribute :>> elementId = "DEF::4411";
        attribute :>> sourceFile = "Rail_MBSE_Function_Interface_v1_final.xlsx";
        attribute :>> sourceSheet = "Product_Hierarchy";
        attribute :>> sourceRow = 88;
    }
    item trace_6907af61c37f06e1 : TraceRecord {
        attribute :>> elementId = "USAGE::4411";
        attribute :>> sourceFile = "Rail_MBSE_Function_Interface_v1_final.xlsx";
        attribute :>> sourceSheet = "Product_Hierarchy";
        attribute :>> sourceRow = 88;
    }
    item trace_7602a3b0eac17c89 : TraceRecord {
        attribute :>> elementId = "DEF::4412";
        attribute :>> sourceFile = "Rail_MBSE_Function_Interface_v1_final.xlsx";
        attribute :>> sourceSheet = "Product_Hierarchy";
        attribute :>> sourceRow = 89;
    }
    item trace_745e7898e1dd2949 : TraceRecord {
        attribute :>> elementId = "USAGE::4412";
        attribute :>> sourceFile = "Rail_MBSE_Function_Interface_v1_final.xlsx";
        attribute :>> sourceSheet = "Product_Hierarchy";
        attribute :>> sourceRow = 89;
    }
    item trace_d581af03504e6222 : TraceRecord {
        attribute :>> elementId = "DEF::4413";
        attribute :>> sourceFile = "Rail_MBSE_Function_Interface_v1_final.xlsx";
        attribute :>> sourceSheet = "Product_Hierarchy";
        attribute :>> sourceRow = 90;
    }
    item trace_76781a4b0bfe5d60 : TraceRecord {
        attribute :>> elementId = "USAGE::4413";
        attribute :>> sourceFile = "Rail_MBSE_Function_Interface_v1_final.xlsx";
        attribute :>> sourceSheet = "Product_Hierarchy";
        attribute :>> sourceRow = 90;
    }
    item trace_6c8c295483aef4f1 : TraceRecord {
        attribute :>> elementId = "DEF::4511";
        attribute :>> sourceFile = "Rail_MBSE_Function_Interface_v1_final.xlsx";
        attribute :>> sourceSheet = "Product_Hierarchy";
        attribute :>> sourceRow = 91;
    }
    item trace_80fec8cb9db5d804 : TraceRecord {
        attribute :>> elementId = "USAGE::4511";
        attribute :>> sourceFile = "Rail_MBSE_Function_Interface_v1_final.xlsx";
        attribute :>> sourceSheet = "Product_Hierarchy";
        attribute :>> sourceRow = 91;
    }
    item trace_54f147563ac8db59 : TraceRecord {
        attribute :>> elementId = "DEF::4513";
        attribute :>> sourceFile = "Rail_MBSE_Function_Interface_v1_final.xlsx";
        attribute :>> sourceSheet = "Product_Hierarchy";
        attribute :>> sourceRow = 92;
    }
    item trace_badae4a2f35a4b1e : TraceRecord {
        attribute :>> elementId = "USAGE::4513";
        attribute :>> sourceFile = "Rail_MBSE_Function_Interface_v1_final.xlsx";
        attribute :>> sourceSheet = "Product_Hierarchy";
        attribute :>> sourceRow = 92;
    }
    item trace_2d0966610fbe8482 : TraceRecord {
        attribute :>> elementId = "DEF::4517";
        attribute :>> sourceFile = "Rail_MBSE_Function_Interface_v1_final.xlsx";
        attribute :>> sourceSheet = "Product_Hierarchy";
        attribute :>> sourceRow = 93;
    }
    item trace_fb99efbb3a44b502 : TraceRecord {
        attribute :>> elementId = "USAGE::4517";
        attribute :>> sourceFile = "Rail_MBSE_Function_Interface_v1_final.xlsx";
        attribute :>> sourceSheet = "Product_Hierarchy";
        attribute :>> sourceRow = 93;
    }
    item trace_bf50dc93a059e610 : TraceRecord {
        attribute :>> elementId = "DEF::4518";
        attribute :>> sourceFile = "Rail_MBSE_Function_Interface_v1_final.xlsx";
        attribute :>> sourceSheet = "Product_Hierarchy";
        attribute :>> sourceRow = 94;
    }
    item trace_c63db3fa420006e3 : TraceRecord {
        attribute :>> elementId = "USAGE::4518";
        attribute :>> sourceFile = "Rail_MBSE_Function_Interface_v1_final.xlsx";
        attribute :>> sourceSheet = "Product_Hierarchy";
        attribute :>> sourceRow = 94;
    }
    item trace_7e8a7deb98d5cf11 : TraceRecord {
        attribute :>> elementId = "DEF::5111";
        attribute :>> sourceFile = "Rail_MBSE_Function_Interface_v1_final.xlsx";
        attribute :>> sourceSheet = "Product_Hierarchy";
        attribute :>> sourceRow = 95;
    }
    item trace_5ac4cce58c0e105f : TraceRecord {
        attribute :>> elementId = "USAGE::5111";
        attribute :>> sourceFile = "Rail_MBSE_Function_Interface_v1_final.xlsx";
        attribute :>> sourceSheet = "Product_Hierarchy";
        attribute :>> sourceRow = 95;
    }
    item trace_127296f0f3e70d17 : TraceRecord {
        attribute :>> elementId = "DEF::5112";
        attribute :>> sourceFile = "Rail_MBSE_Function_Interface_v1_final.xlsx";
        attribute :>> sourceSheet = "Product_Hierarchy";
        attribute :>> sourceRow = 96;
    }
    item trace_73e91e33c4a141c7 : TraceRecord {
        attribute :>> elementId = "USAGE::5112";
        attribute :>> sourceFile = "Rail_MBSE_Function_Interface_v1_final.xlsx";
        attribute :>> sourceSheet = "Product_Hierarchy";
        attribute :>> sourceRow = 96;
    }
    item trace_a75c32564e70bd57 : TraceRecord {
        attribute :>> elementId = "DEF::5113";
        attribute :>> sourceFile = "Rail_MBSE_Function_Interface_v1_final.xlsx";
        attribute :>> sourceSheet = "Product_Hierarchy";
        attribute :>> sourceRow = 97;
    }
    item trace_b3c999a87593e556 : TraceRecord {
        attribute :>> elementId = "USAGE::5113";
        attribute :>> sourceFile = "Rail_MBSE_Function_Interface_v1_final.xlsx";
        attribute :>> sourceSheet = "Product_Hierarchy";
        attribute :>> sourceRow = 97;
    }
    item trace_6f277a10991e366e : TraceRecord {
        attribute :>> elementId = "DEF::5121";
        attribute :>> sourceFile = "Rail_MBSE_Function_Interface_v1_final.xlsx";
        attribute :>> sourceSheet = "Product_Hierarchy";
        attribute :>> sourceRow = 98;
    }
    item trace_36e2e5b5e472fc9b : TraceRecord {
        attribute :>> elementId = "USAGE::5121";
        attribute :>> sourceFile = "Rail_MBSE_Function_Interface_v1_final.xlsx";
        attribute :>> sourceSheet = "Product_Hierarchy";
        attribute :>> sourceRow = 98;
    }
    item trace_78e95102e1316aac : TraceRecord {
        attribute :>> elementId = "DEF::5122";
        attribute :>> sourceFile = "Rail_MBSE_Function_Interface_v1_final.xlsx";
        attribute :>> sourceSheet = "Product_Hierarchy";
        attribute :>> sourceRow = 99;
    }
    item trace_05c46889e04993c5 : TraceRecord {
        attribute :>> elementId = "USAGE::5122";
        attribute :>> sourceFile = "Rail_MBSE_Function_Interface_v1_final.xlsx";
        attribute :>> sourceSheet = "Product_Hierarchy";
        attribute :>> sourceRow = 99;
    }
    item trace_8f44a9538bd869e6 : TraceRecord {
        attribute :>> elementId = "DEF::5131";
        attribute :>> sourceFile = "Rail_MBSE_Function_Interface_v1_final.xlsx";
        attribute :>> sourceSheet = "Product_Hierarchy";
        attribute :>> sourceRow = 100;
    }
    item trace_11ce302656dbf55b : TraceRecord {
        attribute :>> elementId = "USAGE::5131";
        attribute :>> sourceFile = "Rail_MBSE_Function_Interface_v1_final.xlsx";
        attribute :>> sourceSheet = "Product_Hierarchy";
        attribute :>> sourceRow = 100;
    }
    item trace_767383591e0fa6fa : TraceRecord {
        attribute :>> elementId = "DEF::5132";
        attribute :>> sourceFile = "Rail_MBSE_Function_Interface_v1_final.xlsx";
        attribute :>> sourceSheet = "Product_Hierarchy";
        attribute :>> sourceRow = 101;
    }
    item trace_6d28949ce89b5faa : TraceRecord {
        attribute :>> elementId = "USAGE::5132";
        attribute :>> sourceFile = "Rail_MBSE_Function_Interface_v1_final.xlsx";
        attribute :>> sourceSheet = "Product_Hierarchy";
        attribute :>> sourceRow = 101;
    }
    item trace_20229f02118c5951 : TraceRecord {
        attribute :>> elementId = "DEF::5133";
        attribute :>> sourceFile = "Rail_MBSE_Function_Interface_v1_final.xlsx";
        attribute :>> sourceSheet = "Product_Hierarchy";
        attribute :>> sourceRow = 102;
    }
    item trace_dd5ada8f18e7fd8c : TraceRecord {
        attribute :>> elementId = "USAGE::5133";
        attribute :>> sourceFile = "Rail_MBSE_Function_Interface_v1_final.xlsx";
        attribute :>> sourceSheet = "Product_Hierarchy";
        attribute :>> sourceRow = 102;
    }
    item trace_dda3a464d03407be : TraceRecord {
        attribute :>> elementId = "DEF::5142";
        attribute :>> sourceFile = "Rail_MBSE_Function_Interface_v1_final.xlsx";
        attribute :>> sourceSheet = "Product_Hierarchy";
        attribute :>> sourceRow = 103;
    }
    item trace_9f2d5a511a3f0646 : TraceRecord {
        attribute :>> elementId = "USAGE::5142";
        attribute :>> sourceFile = "Rail_MBSE_Function_Interface_v1_final.xlsx";
        attribute :>> sourceSheet = "Product_Hierarchy";
        attribute :>> sourceRow = 103;
    }
    item trace_e30b487d9a4d8fdc : TraceRecord {
        attribute :>> elementId = "DEF::5145";
        attribute :>> sourceFile = "Rail_MBSE_Function_Interface_v1_final.xlsx";
        attribute :>> sourceSheet = "Product_Hierarchy";
        attribute :>> sourceRow = 104;
    }
    item trace_c3497f3fb6f96026 : TraceRecord {
        attribute :>> elementId = "USAGE::5145";
        attribute :>> sourceFile = "Rail_MBSE_Function_Interface_v1_final.xlsx";
        attribute :>> sourceSheet = "Product_Hierarchy";
        attribute :>> sourceRow = 104;
    }
    item trace_e7b6e6acd182dd52 : TraceRecord {
        attribute :>> elementId = "DEF::5311";
        attribute :>> sourceFile = "Rail_MBSE_Function_Interface_v1_final.xlsx";
        attribute :>> sourceSheet = "Product_Hierarchy";
        attribute :>> sourceRow = 105;
    }
    item trace_a8a41156adeb4239 : TraceRecord {
        attribute :>> elementId = "USAGE::5311";
        attribute :>> sourceFile = "Rail_MBSE_Function_Interface_v1_final.xlsx";
        attribute :>> sourceSheet = "Product_Hierarchy";
        attribute :>> sourceRow = 105;
    }
    item trace_9541621f9789a162 : TraceRecord {
        attribute :>> elementId = "DEF::7124";
        attribute :>> sourceFile = "Rail_MBSE_Function_Interface_v1_final.xlsx";
        attribute :>> sourceSheet = "Product_Hierarchy";
        attribute :>> sourceRow = 106;
    }
    item trace_38ec5d273a9d364c : TraceRecord {
        attribute :>> elementId = "USAGE::7124";
        attribute :>> sourceFile = "Rail_MBSE_Function_Interface_v1_final.xlsx";
        attribute :>> sourceSheet = "Product_Hierarchy";
        attribute :>> sourceRow = 106;
    }
    item trace_3998a8f5d8a7ffab : TraceRecord {
        attribute :>> elementId = "DEF::7131";
        attribute :>> sourceFile = "Rail_MBSE_Function_Interface_v1_final.xlsx";
        attribute :>> sourceSheet = "Product_Hierarchy";
        attribute :>> sourceRow = 107;
    }
    item trace_52500a5d8e302dae : TraceRecord {
        attribute :>> elementId = "USAGE::7131";
        attribute :>> sourceFile = "Rail_MBSE_Function_Interface_v1_final.xlsx";
        attribute :>> sourceSheet = "Product_Hierarchy";
        attribute :>> sourceRow = 107;
    }
    item trace_42ee41421f12263f : TraceRecord {
        attribute :>> elementId = "DEF::7142";
        attribute :>> sourceFile = "Rail_MBSE_Function_Interface_v1_final.xlsx";
        attribute :>> sourceSheet = "Product_Hierarchy";
        attribute :>> sourceRow = 108;
    }
    item trace_cb7e93aacca6db7c : TraceRecord {
        attribute :>> elementId = "USAGE::7142";
        attribute :>> sourceFile = "Rail_MBSE_Function_Interface_v1_final.xlsx";
        attribute :>> sourceSheet = "Product_Hierarchy";
        attribute :>> sourceRow = 108;
    }
    item trace_5b1d3d4db99efc4f : TraceRecord {
        attribute :>> elementId = "DEF::7211";
        attribute :>> sourceFile = "Rail_MBSE_Function_Interface_v1_final.xlsx";
        attribute :>> sourceSheet = "Product_Hierarchy";
        attribute :>> sourceRow = 109;
    }
    item trace_c58a034ccffc77a4 : TraceRecord {
        attribute :>> elementId = "USAGE::7211";
        attribute :>> sourceFile = "Rail_MBSE_Function_Interface_v1_final.xlsx";
        attribute :>> sourceSheet = "Product_Hierarchy";
        attribute :>> sourceRow = 109;
    }
    item trace_959ced77bc097688 : TraceRecord {
        attribute :>> elementId = "DEF::7213";
        attribute :>> sourceFile = "Rail_MBSE_Function_Interface_v1_final.xlsx";
        attribute :>> sourceSheet = "Product_Hierarchy";
        attribute :>> sourceRow = 110;
    }
    item trace_3ebaf992923c622d : TraceRecord {
        attribute :>> elementId = "USAGE::7213";
        attribute :>> sourceFile = "Rail_MBSE_Function_Interface_v1_final.xlsx";
        attribute :>> sourceSheet = "Product_Hierarchy";
        attribute :>> sourceRow = 110;
    }
    item trace_84fa62aa84941ae8 : TraceRecord {
        attribute :>> elementId = "DEF::7222";
        attribute :>> sourceFile = "Rail_MBSE_Function_Interface_v1_final.xlsx";
        attribute :>> sourceSheet = "Product_Hierarchy";
        attribute :>> sourceRow = 111;
    }
    item trace_f443f178fb0efd33 : TraceRecord {
        attribute :>> elementId = "USAGE::7222";
        attribute :>> sourceFile = "Rail_MBSE_Function_Interface_v1_final.xlsx";
        attribute :>> sourceSheet = "Product_Hierarchy";
        attribute :>> sourceRow = 111;
    }
    item trace_7c2c15e03312d7b3 : TraceRecord {
        attribute :>> elementId = "DEF::7223";
        attribute :>> sourceFile = "Rail_MBSE_Function_Interface_v1_final.xlsx";
        attribute :>> sourceSheet = "Product_Hierarchy";
        attribute :>> sourceRow = 112;
    }
    item trace_c1f6317fc61beabe : TraceRecord {
        attribute :>> elementId = "USAGE::7223";
        attribute :>> sourceFile = "Rail_MBSE_Function_Interface_v1_final.xlsx";
        attribute :>> sourceSheet = "Product_Hierarchy";
        attribute :>> sourceRow = 112;
    }
    item trace_305dfd67f5a78ea1 : TraceRecord {
        attribute :>> elementId = "DEF::7224";
        attribute :>> sourceFile = "Rail_MBSE_Function_Interface_v1_final.xlsx";
        attribute :>> sourceSheet = "Product_Hierarchy";
        attribute :>> sourceRow = 113;
    }
    item trace_58a91f88330c98e8 : TraceRecord {
        attribute :>> elementId = "USAGE::7224";
        attribute :>> sourceFile = "Rail_MBSE_Function_Interface_v1_final.xlsx";
        attribute :>> sourceSheet = "Product_Hierarchy";
        attribute :>> sourceRow = 113;
    }
    item trace_55891c260aa2dcc0 : TraceRecord {
        attribute :>> elementId = "DEF::7225";
        attribute :>> sourceFile = "Rail_MBSE_Function_Interface_v1_final.xlsx";
        attribute :>> sourceSheet = "Product_Hierarchy";
        attribute :>> sourceRow = 114;
    }
    item trace_e992d249ddca5fe5 : TraceRecord {
        attribute :>> elementId = "USAGE::7225";
        attribute :>> sourceFile = "Rail_MBSE_Function_Interface_v1_final.xlsx";
        attribute :>> sourceSheet = "Product_Hierarchy";
        attribute :>> sourceRow = 114;
    }
    item trace_fea8184eb99dcc8b : TraceRecord {
        attribute :>> elementId = "DEF::7226";
        attribute :>> sourceFile = "Rail_MBSE_Function_Interface_v1_final.xlsx";
        attribute :>> sourceSheet = "Product_Hierarchy";
        attribute :>> sourceRow = 115;
    }
    item trace_3e90b246ed1f7f45 : TraceRecord {
        attribute :>> elementId = "USAGE::7226";
        attribute :>> sourceFile = "Rail_MBSE_Function_Interface_v1_final.xlsx";
        attribute :>> sourceSheet = "Product_Hierarchy";
        attribute :>> sourceRow = 115;
    }
    item trace_12b0ed2369e3b75d : TraceRecord {
        attribute :>> elementId = "DEF::7227";
        attribute :>> sourceFile = "Rail_MBSE_Function_Interface_v1_final.xlsx";
        attribute :>> sourceSheet = "Product_Hierarchy";
        attribute :>> sourceRow = 116;
    }
    item trace_7ced450401489e16 : TraceRecord {
        attribute :>> elementId = "USAGE::7227";
        attribute :>> sourceFile = "Rail_MBSE_Function_Interface_v1_final.xlsx";
        attribute :>> sourceSheet = "Product_Hierarchy";
        attribute :>> sourceRow = 116;
    }
    item trace_949c52d3c4d76c34 : TraceRecord {
        attribute :>> elementId = "DEF::7228";
        attribute :>> sourceFile = "Rail_MBSE_Function_Interface_v1_final.xlsx";
        attribute :>> sourceSheet = "Product_Hierarchy";
        attribute :>> sourceRow = 117;
    }
    item trace_5c1792b083f2f102 : TraceRecord {
        attribute :>> elementId = "USAGE::7228";
        attribute :>> sourceFile = "Rail_MBSE_Function_Interface_v1_final.xlsx";
        attribute :>> sourceSheet = "Product_Hierarchy";
        attribute :>> sourceRow = 117;
    }
    item trace_a1afd4f0af1acd59 : TraceRecord {
        attribute :>> elementId = "DEF::7229";
        attribute :>> sourceFile = "Rail_MBSE_Function_Interface_v1_final.xlsx";
        attribute :>> sourceSheet = "Product_Hierarchy";
        attribute :>> sourceRow = 118;
    }
    item trace_48f9bae02fbecca4 : TraceRecord {
        attribute :>> elementId = "USAGE::7229";
        attribute :>> sourceFile = "Rail_MBSE_Function_Interface_v1_final.xlsx";
        attribute :>> sourceSheet = "Product_Hierarchy";
        attribute :>> sourceRow = 118;
    }
    item trace_42e0ccb76a6237b1 : TraceRecord {
        attribute :>> elementId = "DEF::722A";
        attribute :>> sourceFile = "Rail_MBSE_Function_Interface_v1_final.xlsx";
        attribute :>> sourceSheet = "Product_Hierarchy";
        attribute :>> sourceRow = 119;
    }
    item trace_80cec3d221665a7a : TraceRecord {
        attribute :>> elementId = "USAGE::722A";
        attribute :>> sourceFile = "Rail_MBSE_Function_Interface_v1_final.xlsx";
        attribute :>> sourceSheet = "Product_Hierarchy";
        attribute :>> sourceRow = 119;
    }
    item trace_1e40558ed602cb36 : TraceRecord {
        attribute :>> elementId = "DEF::722B";
        attribute :>> sourceFile = "Rail_MBSE_Function_Interface_v1_final.xlsx";
        attribute :>> sourceSheet = "Product_Hierarchy";
        attribute :>> sourceRow = 120;
    }
    item trace_a4456fe6318510e1 : TraceRecord {
        attribute :>> elementId = "USAGE::722B";
        attribute :>> sourceFile = "Rail_MBSE_Function_Interface_v1_final.xlsx";
        attribute :>> sourceSheet = "Product_Hierarchy";
        attribute :>> sourceRow = 120;
    }
    item trace_078097e762180700 : TraceRecord {
        attribute :>> elementId = "DEF::722C";
        attribute :>> sourceFile = "Rail_MBSE_Function_Interface_v1_final.xlsx";
        attribute :>> sourceSheet = "Product_Hierarchy";
        attribute :>> sourceRow = 121;
    }
    item trace_9b089e8f2d7fbe6a : TraceRecord {
        attribute :>> elementId = "USAGE::722C";
        attribute :>> sourceFile = "Rail_MBSE_Function_Interface_v1_final.xlsx";
        attribute :>> sourceSheet = "Product_Hierarchy";
        attribute :>> sourceRow = 121;
    }
    item trace_7519eb74c8f0be20 : TraceRecord {
        attribute :>> elementId = "DEF::7252";
        attribute :>> sourceFile = "Rail_MBSE_Function_Interface_v1_final.xlsx";
        attribute :>> sourceSheet = "Product_Hierarchy";
        attribute :>> sourceRow = 122;
    }
    item trace_92f667423c258586 : TraceRecord {
        attribute :>> elementId = "USAGE::7252";
        attribute :>> sourceFile = "Rail_MBSE_Function_Interface_v1_final.xlsx";
        attribute :>> sourceSheet = "Product_Hierarchy";
        attribute :>> sourceRow = 122;
    }
    item trace_34690a63c97ccb82 : TraceRecord {
        attribute :>> elementId = "DEF::7254";
        attribute :>> sourceFile = "Rail_MBSE_Function_Interface_v1_final.xlsx";
        attribute :>> sourceSheet = "Product_Hierarchy";
        attribute :>> sourceRow = 123;
    }
    item trace_42b78abeb785b30d : TraceRecord {
        attribute :>> elementId = "USAGE::7254";
        attribute :>> sourceFile = "Rail_MBSE_Function_Interface_v1_final.xlsx";
        attribute :>> sourceSheet = "Product_Hierarchy";
        attribute :>> sourceRow = 123;
    }
    item trace_00dca975a62eeb66 : TraceRecord {
        attribute :>> elementId = "DEF::7255";
        attribute :>> sourceFile = "Rail_MBSE_Function_Interface_v1_final.xlsx";
        attribute :>> sourceSheet = "Product_Hierarchy";
        attribute :>> sourceRow = 124;
    }
    item trace_7465e147073ffe2f : TraceRecord {
        attribute :>> elementId = "USAGE::7255";
        attribute :>> sourceFile = "Rail_MBSE_Function_Interface_v1_final.xlsx";
        attribute :>> sourceSheet = "Product_Hierarchy";
        attribute :>> sourceRow = 124;
    }
    item trace_2cb6c472b0c9ae59 : TraceRecord {
        attribute :>> elementId = "DEF::7281";
        attribute :>> sourceFile = "Rail_MBSE_Function_Interface_v1_final.xlsx";
        attribute :>> sourceSheet = "Product_Hierarchy";
        attribute :>> sourceRow = 125;
    }
    item trace_20f981d0d916bbfd : TraceRecord {
        attribute :>> elementId = "USAGE::7281";
        attribute :>> sourceFile = "Rail_MBSE_Function_Interface_v1_final.xlsx";
        attribute :>> sourceSheet = "Product_Hierarchy";
        attribute :>> sourceRow = 125;
    }
    item trace_a90713867173fd96 : TraceRecord {
        attribute :>> elementId = "DEF::7284";
        attribute :>> sourceFile = "Rail_MBSE_Function_Interface_v1_final.xlsx";
        attribute :>> sourceSheet = "Product_Hierarchy";
        attribute :>> sourceRow = 126;
    }
    item trace_e37cbb17e5002339 : TraceRecord {
        attribute :>> elementId = "USAGE::7284";
        attribute :>> sourceFile = "Rail_MBSE_Function_Interface_v1_final.xlsx";
        attribute :>> sourceSheet = "Product_Hierarchy";
        attribute :>> sourceRow = 126;
    }
    item trace_d33e3de773444b0c : TraceRecord {
        attribute :>> elementId = "DEF::7285";
        attribute :>> sourceFile = "Rail_MBSE_Function_Interface_v1_final.xlsx";
        attribute :>> sourceSheet = "Product_Hierarchy";
        attribute :>> sourceRow = 127;
    }
    item trace_e82e8630412b8344 : TraceRecord {
        attribute :>> elementId = "USAGE::7285";
        attribute :>> sourceFile = "Rail_MBSE_Function_Interface_v1_final.xlsx";
        attribute :>> sourceSheet = "Product_Hierarchy";
        attribute :>> sourceRow = 127;
    }
    item trace_8fb81f92aae52602 : TraceRecord {
        attribute :>> elementId = "DEF::8121";
        attribute :>> sourceFile = "Rail_MBSE_Function_Interface_v1_final.xlsx";
        attribute :>> sourceSheet = "Product_Hierarchy";
        attribute :>> sourceRow = 128;
    }
    item trace_2d9ab90bf8ace7be : TraceRecord {
        attribute :>> elementId = "USAGE::8121";
        attribute :>> sourceFile = "Rail_MBSE_Function_Interface_v1_final.xlsx";
        attribute :>> sourceSheet = "Product_Hierarchy";
        attribute :>> sourceRow = 128;
    }
    item trace_217b09f81ee9b066 : TraceRecord {
        attribute :>> elementId = "DEF::8122";
        attribute :>> sourceFile = "Rail_MBSE_Function_Interface_v1_final.xlsx";
        attribute :>> sourceSheet = "Product_Hierarchy";
        attribute :>> sourceRow = 129;
    }
    item trace_29b89a524d4a80ab : TraceRecord {
        attribute :>> elementId = "USAGE::8122";
        attribute :>> sourceFile = "Rail_MBSE_Function_Interface_v1_final.xlsx";
        attribute :>> sourceSheet = "Product_Hierarchy";
        attribute :>> sourceRow = 129;
    }
    item trace_579295a8ad060871 : TraceRecord {
        attribute :>> elementId = "DEF::8125";
        attribute :>> sourceFile = "Rail_MBSE_Function_Interface_v1_final.xlsx";
        attribute :>> sourceSheet = "Product_Hierarchy";
        attribute :>> sourceRow = 130;
    }
    item trace_80b69e7d9e31659a : TraceRecord {
        attribute :>> elementId = "USAGE::8125";
        attribute :>> sourceFile = "Rail_MBSE_Function_Interface_v1_final.xlsx";
        attribute :>> sourceSheet = "Product_Hierarchy";
        attribute :>> sourceRow = 130;
    }
    item trace_e535beb14b140d2d : TraceRecord {
        attribute :>> elementId = "DEF::8127";
        attribute :>> sourceFile = "Rail_MBSE_Function_Interface_v1_final.xlsx";
        attribute :>> sourceSheet = "Product_Hierarchy";
        attribute :>> sourceRow = 131;
    }
    item trace_2daed0cf26a6aaca : TraceRecord {
        attribute :>> elementId = "USAGE::8127";
        attribute :>> sourceFile = "Rail_MBSE_Function_Interface_v1_final.xlsx";
        attribute :>> sourceSheet = "Product_Hierarchy";
        attribute :>> sourceRow = 131;
    }
    item trace_33b1fae2179192ee : TraceRecord {
        attribute :>> elementId = "DEF::8128";
        attribute :>> sourceFile = "Rail_MBSE_Function_Interface_v1_final.xlsx";
        attribute :>> sourceSheet = "Product_Hierarchy";
        attribute :>> sourceRow = 132;
    }
    item trace_b19afe8645f31049 : TraceRecord {
        attribute :>> elementId = "USAGE::8128";
        attribute :>> sourceFile = "Rail_MBSE_Function_Interface_v1_final.xlsx";
        attribute :>> sourceSheet = "Product_Hierarchy";
        attribute :>> sourceRow = 132;
    }
    item trace_151633ac41e59363 : TraceRecord {
        attribute :>> elementId = "DEF::8151";
        attribute :>> sourceFile = "Rail_MBSE_Function_Interface_v1_final.xlsx";
        attribute :>> sourceSheet = "Product_Hierarchy";
        attribute :>> sourceRow = 133;
    }
    item trace_91f58ef4be0e83b2 : TraceRecord {
        attribute :>> elementId = "USAGE::8151";
        attribute :>> sourceFile = "Rail_MBSE_Function_Interface_v1_final.xlsx";
        attribute :>> sourceSheet = "Product_Hierarchy";
        attribute :>> sourceRow = 133;
    }
    item trace_b3b636d2c64cb4ae : TraceRecord {
        attribute :>> elementId = "DEF::8152";
        attribute :>> sourceFile = "Rail_MBSE_Function_Interface_v1_final.xlsx";
        attribute :>> sourceSheet = "Product_Hierarchy";
        attribute :>> sourceRow = 134;
    }
    item trace_8a1369d5040fb96d : TraceRecord {
        attribute :>> elementId = "USAGE::8152";
        attribute :>> sourceFile = "Rail_MBSE_Function_Interface_v1_final.xlsx";
        attribute :>> sourceSheet = "Product_Hierarchy";
        attribute :>> sourceRow = 134;
    }
    item trace_4c43763171ea7e19 : TraceRecord {
        attribute :>> elementId = "DEF::8154";
        attribute :>> sourceFile = "Rail_MBSE_Function_Interface_v1_final.xlsx";
        attribute :>> sourceSheet = "Product_Hierarchy";
        attribute :>> sourceRow = 135;
    }
    item trace_eecbd116c079eda8 : TraceRecord {
        attribute :>> elementId = "USAGE::8154";
        attribute :>> sourceFile = "Rail_MBSE_Function_Interface_v1_final.xlsx";
        attribute :>> sourceSheet = "Product_Hierarchy";
        attribute :>> sourceRow = 135;
    }
    item trace_9b71b859a592f19a : TraceRecord {
        attribute :>> elementId = "DEF::8166";
        attribute :>> sourceFile = "Rail_MBSE_Function_Interface_v1_final.xlsx";
        attribute :>> sourceSheet = "Product_Hierarchy";
        attribute :>> sourceRow = 136;
    }
    item trace_bd667389e5f121e6 : TraceRecord {
        attribute :>> elementId = "USAGE::8166";
        attribute :>> sourceFile = "Rail_MBSE_Function_Interface_v1_final.xlsx";
        attribute :>> sourceSheet = "Product_Hierarchy";
        attribute :>> sourceRow = 136;
    }
    item trace_f8cb217d4c6e30b6 : TraceRecord {
        attribute :>> elementId = "DEF::D112";
        attribute :>> sourceFile = "Rail_MBSE_Function_Interface_v1_final.xlsx";
        attribute :>> sourceSheet = "Product_Hierarchy";
        attribute :>> sourceRow = 137;
    }
    item trace_2c766d6d8a01db48 : TraceRecord {
        attribute :>> elementId = "USAGE::D112";
        attribute :>> sourceFile = "Rail_MBSE_Function_Interface_v1_final.xlsx";
        attribute :>> sourceSheet = "Product_Hierarchy";
        attribute :>> sourceRow = 137;
    }
    item trace_88e452062d43f892 : TraceRecord {
        attribute :>> elementId = "DEF::D113";
        attribute :>> sourceFile = "Rail_MBSE_Function_Interface_v1_final.xlsx";
        attribute :>> sourceSheet = "Product_Hierarchy";
        attribute :>> sourceRow = 138;
    }
    item trace_9a45c172b78dc1b3 : TraceRecord {
        attribute :>> elementId = "USAGE::D113";
        attribute :>> sourceFile = "Rail_MBSE_Function_Interface_v1_final.xlsx";
        attribute :>> sourceSheet = "Product_Hierarchy";
        attribute :>> sourceRow = 138;
    }
    item trace_30aed6804714b767 : TraceRecord {
        attribute :>> elementId = "DEF::D114";
        attribute :>> sourceFile = "Rail_MBSE_Function_Interface_v1_final.xlsx";
        attribute :>> sourceSheet = "Product_Hierarchy";
        attribute :>> sourceRow = 139;
    }
    item trace_c1693bf1ffc6d698 : TraceRecord {
        attribute :>> elementId = "USAGE::D114";
        attribute :>> sourceFile = "Rail_MBSE_Function_Interface_v1_final.xlsx";
        attribute :>> sourceSheet = "Product_Hierarchy";
        attribute :>> sourceRow = 139;
    }
    item trace_b84de9abbabf9c84 : TraceRecord {
        attribute :>> elementId = "DEF::D121";
        attribute :>> sourceFile = "Rail_MBSE_Function_Interface_v1_final.xlsx";
        attribute :>> sourceSheet = "Product_Hierarchy";
        attribute :>> sourceRow = 140;
    }
    item trace_855456710b5e68d9 : TraceRecord {
        attribute :>> elementId = "USAGE::D121";
        attribute :>> sourceFile = "Rail_MBSE_Function_Interface_v1_final.xlsx";
        attribute :>> sourceSheet = "Product_Hierarchy";
        attribute :>> sourceRow = 140;
    }
    item trace_2c2acad207ab6426 : TraceRecord {
        attribute :>> elementId = "DEF::D13B";
        attribute :>> sourceFile = "Rail_MBSE_Function_Interface_v1_final.xlsx";
        attribute :>> sourceSheet = "Product_Hierarchy";
        attribute :>> sourceRow = 141;
    }
    item trace_bbe82d8d6fb79800 : TraceRecord {
        attribute :>> elementId = "USAGE::D13B";
        attribute :>> sourceFile = "Rail_MBSE_Function_Interface_v1_final.xlsx";
        attribute :>> sourceSheet = "Product_Hierarchy";
        attribute :>> sourceRow = 141;
    }
    item trace_2ce9833f4a2f64ff : TraceRecord {
        attribute :>> elementId = "DEF::X111";
        attribute :>> sourceFile = "Rail_MBSE_Function_Interface_v1_final.xlsx";
        attribute :>> sourceSheet = "Product_Hierarchy";
        attribute :>> sourceRow = 142;
    }
    item trace_2c4eb3aae7304a53 : TraceRecord {
        attribute :>> elementId = "USAGE::X111";
        attribute :>> sourceFile = "Rail_MBSE_Function_Interface_v1_final.xlsx";
        attribute :>> sourceSheet = "Product_Hierarchy";
        attribute :>> sourceRow = 142;
    }
    item trace_8eb7f59fbce875ad : TraceRecord {
        attribute :>> elementId = "DEF::X112";
        attribute :>> sourceFile = "Rail_MBSE_Function_Interface_v1_final.xlsx";
        attribute :>> sourceSheet = "Product_Hierarchy";
        attribute :>> sourceRow = 143;
    }
    item trace_48740ddbab1c210e : TraceRecord {
        attribute :>> elementId = "USAGE::X112";
        attribute :>> sourceFile = "Rail_MBSE_Function_Interface_v1_final.xlsx";
        attribute :>> sourceSheet = "Product_Hierarchy";
        attribute :>> sourceRow = 143;
    }
    item trace_53e879bd64556fc8 : TraceRecord {
        attribute :>> elementId = "DEF::X113";
        attribute :>> sourceFile = "Rail_MBSE_Function_Interface_v1_final.xlsx";
        attribute :>> sourceSheet = "Product_Hierarchy";
        attribute :>> sourceRow = 144;
    }
    item trace_545ff60404562b68 : TraceRecord {
        attribute :>> elementId = "USAGE::X113";
        attribute :>> sourceFile = "Rail_MBSE_Function_Interface_v1_final.xlsx";
        attribute :>> sourceSheet = "Product_Hierarchy";
        attribute :>> sourceRow = 144;
    }
    item trace_34b9099315573b50 : TraceRecord {
        attribute :>> elementId = "DEF::X121";
        attribute :>> sourceFile = "Rail_MBSE_Function_Interface_v1_final.xlsx";
        attribute :>> sourceSheet = "Product_Hierarchy";
        attribute :>> sourceRow = 145;
    }
    item trace_95c196c15d7dadd0 : TraceRecord {
        attribute :>> elementId = "USAGE::X121";
        attribute :>> sourceFile = "Rail_MBSE_Function_Interface_v1_final.xlsx";
        attribute :>> sourceSheet = "Product_Hierarchy";
        attribute :>> sourceRow = 145;
    }
    item trace_aa323d3e3ffd4193 : TraceRecord {
        attribute :>> elementId = "DEF::X122";
        attribute :>> sourceFile = "Rail_MBSE_Function_Interface_v1_final.xlsx";
        attribute :>> sourceSheet = "Product_Hierarchy";
        attribute :>> sourceRow = 146;
    }
    item trace_04f21f9e347e8930 : TraceRecord {
        attribute :>> elementId = "USAGE::X122";
        attribute :>> sourceFile = "Rail_MBSE_Function_Interface_v1_final.xlsx";
        attribute :>> sourceSheet = "Product_Hierarchy";
        attribute :>> sourceRow = 146;
    }
    item trace_a4ec654d3d5035ca : TraceRecord {
        attribute :>> elementId = "DEF::X123";
        attribute :>> sourceFile = "Rail_MBSE_Function_Interface_v1_final.xlsx";
        attribute :>> sourceSheet = "Product_Hierarchy";
        attribute :>> sourceRow = 147;
    }
    item trace_5637b044b81be5fb : TraceRecord {
        attribute :>> elementId = "USAGE::X123";
        attribute :>> sourceFile = "Rail_MBSE_Function_Interface_v1_final.xlsx";
        attribute :>> sourceSheet = "Product_Hierarchy";
        attribute :>> sourceRow = 147;
    }
    item trace_4c09387e678c5a32 : TraceRecord {
        attribute :>> elementId = "DEF::X124";
        attribute :>> sourceFile = "Rail_MBSE_Function_Interface_v1_final.xlsx";
        attribute :>> sourceSheet = "Product_Hierarchy";
        attribute :>> sourceRow = 148;
    }
    item trace_5d70acb3f5653c01 : TraceRecord {
        attribute :>> elementId = "USAGE::X124";
        attribute :>> sourceFile = "Rail_MBSE_Function_Interface_v1_final.xlsx";
        attribute :>> sourceSheet = "Product_Hierarchy";
        attribute :>> sourceRow = 148;
    }
    item trace_9ed93e4ca542931d : TraceRecord {
        attribute :>> elementId = "DEF::X131";
        attribute :>> sourceFile = "Rail_MBSE_Function_Interface_v1_final.xlsx";
        attribute :>> sourceSheet = "Product_Hierarchy";
        attribute :>> sourceRow = 149;
    }
    item trace_b2941aa3922e285d : TraceRecord {
        attribute :>> elementId = "USAGE::X131";
        attribute :>> sourceFile = "Rail_MBSE_Function_Interface_v1_final.xlsx";
        attribute :>> sourceSheet = "Product_Hierarchy";
        attribute :>> sourceRow = 149;
    }
    item trace_7cbc10ce7fd81f00 : TraceRecord {
        attribute :>> elementId = "DEF::X132";
        attribute :>> sourceFile = "Rail_MBSE_Function_Interface_v1_final.xlsx";
        attribute :>> sourceSheet = "Product_Hierarchy";
        attribute :>> sourceRow = 150;
    }
    item trace_515e329968ada29e : TraceRecord {
        attribute :>> elementId = "USAGE::X132";
        attribute :>> sourceFile = "Rail_MBSE_Function_Interface_v1_final.xlsx";
        attribute :>> sourceSheet = "Product_Hierarchy";
        attribute :>> sourceRow = 150;
    }
    item trace_49a01b4ebf96bbc5 : TraceRecord {
        attribute :>> elementId = "DEF::X133";
        attribute :>> sourceFile = "Rail_MBSE_Function_Interface_v1_final.xlsx";
        attribute :>> sourceSheet = "Product_Hierarchy";
        attribute :>> sourceRow = 151;
    }
    item trace_bf504daaa4dc8e55 : TraceRecord {
        attribute :>> elementId = "USAGE::X133";
        attribute :>> sourceFile = "Rail_MBSE_Function_Interface_v1_final.xlsx";
        attribute :>> sourceSheet = "Product_Hierarchy";
        attribute :>> sourceRow = 151;
    }
    item trace_6fe7ff43b39f304a : TraceRecord {
        attribute :>> elementId = "ITEM::ITM-ACC-001";
        attribute :>> sourceFile = "Rail_MBSE_Function_Interface_v1_final.xlsx";
        attribute :>> sourceSheet = "Item";
        attribute :>> sourceRow = 5;
    }
    item trace_9268effc802b6370 : TraceRecord {
        attribute :>> elementId = "PORTTYPE::PT-ACC-001";
        attribute :>> sourceFile = "Rail_MBSE_Function_Interface_v1_final.xlsx";
        attribute :>> sourceSheet = "Item";
        attribute :>> sourceRow = 5;
    }
    item trace_3dadcaea4d9a57a4 : TraceRecord {
        attribute :>> elementId = "INTERFACETYPE::IF-ACC-001";
        attribute :>> sourceFile = "Rail_MBSE_Function_Interface_v1_final.xlsx";
        attribute :>> sourceSheet = "Item";
        attribute :>> sourceRow = 5;
    }
    item trace_1693ade079836abd : TraceRecord {
        attribute :>> elementId = "ITEM::ITM-ACC-002";
        attribute :>> sourceFile = "Rail_MBSE_Function_Interface_v1_final.xlsx";
        attribute :>> sourceSheet = "Item";
        attribute :>> sourceRow = 6;
    }
    item trace_fee36a9911bf92f8 : TraceRecord {
        attribute :>> elementId = "PORTTYPE::PT-ACC-002";
        attribute :>> sourceFile = "Rail_MBSE_Function_Interface_v1_final.xlsx";
        attribute :>> sourceSheet = "Item";
        attribute :>> sourceRow = 6;
    }
    item trace_402e55e76f66cfca : TraceRecord {
        attribute :>> elementId = "INTERFACETYPE::IF-ACC-002";
        attribute :>> sourceFile = "Rail_MBSE_Function_Interface_v1_final.xlsx";
        attribute :>> sourceSheet = "Item";
        attribute :>> sourceRow = 6;
    }
    item trace_a559e1f549712425 : TraceRecord {
        attribute :>> elementId = "ITEM::ITM-ACC-003";
        attribute :>> sourceFile = "Rail_MBSE_Function_Interface_v1_final.xlsx";
        attribute :>> sourceSheet = "Item";
        attribute :>> sourceRow = 7;
    }
    item trace_aa91419eb6b09328 : TraceRecord {
        attribute :>> elementId = "PORTTYPE::PT-ACC-003";
        attribute :>> sourceFile = "Rail_MBSE_Function_Interface_v1_final.xlsx";
        attribute :>> sourceSheet = "Item";
        attribute :>> sourceRow = 7;
    }
    item trace_6b3d17016942255c : TraceRecord {
        attribute :>> elementId = "INTERFACETYPE::IF-ACC-003";
        attribute :>> sourceFile = "Rail_MBSE_Function_Interface_v1_final.xlsx";
        attribute :>> sourceSheet = "Item";
        attribute :>> sourceRow = 7;
    }
    item trace_052dae60b190a5f4 : TraceRecord {
        attribute :>> elementId = "ITEM::ITM-ACC-004";
        attribute :>> sourceFile = "Rail_MBSE_Function_Interface_v1_final.xlsx";
        attribute :>> sourceSheet = "Item";
        attribute :>> sourceRow = 8;
    }
    item trace_9b539415528e1241 : TraceRecord {
        attribute :>> elementId = "PORTTYPE::PT-ACC-004";
        attribute :>> sourceFile = "Rail_MBSE_Function_Interface_v1_final.xlsx";
        attribute :>> sourceSheet = "Item";
        attribute :>> sourceRow = 8;
    }
    item trace_684dabef22e4ea2b : TraceRecord {
        attribute :>> elementId = "INTERFACETYPE::IF-ACC-004";
        attribute :>> sourceFile = "Rail_MBSE_Function_Interface_v1_final.xlsx";
        attribute :>> sourceSheet = "Item";
        attribute :>> sourceRow = 8;
    }
    item trace_d4af4236dae936fd : TraceRecord {
        attribute :>> elementId = "ITEM::ITM-ACC-005";
        attribute :>> sourceFile = "Rail_MBSE_Function_Interface_v1_final.xlsx";
        attribute :>> sourceSheet = "Item";
        attribute :>> sourceRow = 9;
    }
    item trace_bbee67e2b7f2f57d : TraceRecord {
        attribute :>> elementId = "PORTTYPE::PT-ACC-005";
        attribute :>> sourceFile = "Rail_MBSE_Function_Interface_v1_final.xlsx";
        attribute :>> sourceSheet = "Item";
        attribute :>> sourceRow = 9;
    }
    item trace_04763b5d0bf1eb5c : TraceRecord {
        attribute :>> elementId = "INTERFACETYPE::IF-ACC-005";
        attribute :>> sourceFile = "Rail_MBSE_Function_Interface_v1_final.xlsx";
        attribute :>> sourceSheet = "Item";
        attribute :>> sourceRow = 9;
    }
    item trace_8fa176e4cdced7d6 : TraceRecord {
        attribute :>> elementId = "ITEM::ITM-ACC-006";
        attribute :>> sourceFile = "Rail_MBSE_Function_Interface_v1_final.xlsx";
        attribute :>> sourceSheet = "Item";
        attribute :>> sourceRow = 10;
    }
    item trace_63d0bab153c607e3 : TraceRecord {
        attribute :>> elementId = "PORTTYPE::PT-ACC-006";
        attribute :>> sourceFile = "Rail_MBSE_Function_Interface_v1_final.xlsx";
        attribute :>> sourceSheet = "Item";
        attribute :>> sourceRow = 10;
    }
    item trace_62e79220c83cc5b7 : TraceRecord {
        attribute :>> elementId = "INTERFACETYPE::IF-ACC-006";
        attribute :>> sourceFile = "Rail_MBSE_Function_Interface_v1_final.xlsx";
        attribute :>> sourceSheet = "Item";
        attribute :>> sourceRow = 10;
    }
    item trace_afdeda8f0fbe4de9 : TraceRecord {
        attribute :>> elementId = "ITEM::ITM-ACC-007";
        attribute :>> sourceFile = "Rail_MBSE_Function_Interface_v1_final.xlsx";
        attribute :>> sourceSheet = "Item";
        attribute :>> sourceRow = 11;
    }
    item trace_dea28f2a0f977e9d : TraceRecord {
        attribute :>> elementId = "PORTTYPE::PT-ACC-007";
        attribute :>> sourceFile = "Rail_MBSE_Function_Interface_v1_final.xlsx";
        attribute :>> sourceSheet = "Item";
        attribute :>> sourceRow = 11;
    }
    item trace_13765487ac63fe31 : TraceRecord {
        attribute :>> elementId = "INTERFACETYPE::IF-ACC-007";
        attribute :>> sourceFile = "Rail_MBSE_Function_Interface_v1_final.xlsx";
        attribute :>> sourceSheet = "Item";
        attribute :>> sourceRow = 11;
    }
    item trace_70eb706f574d3e51 : TraceRecord {
        attribute :>> elementId = "ITEM::ITM-ACC-008";
        attribute :>> sourceFile = "Rail_MBSE_Function_Interface_v1_final.xlsx";
        attribute :>> sourceSheet = "Item";
        attribute :>> sourceRow = 12;
    }
    item trace_b2e4df9ecb216b0c : TraceRecord {
        attribute :>> elementId = "PORTTYPE::PT-ACC-008";
        attribute :>> sourceFile = "Rail_MBSE_Function_Interface_v1_final.xlsx";
        attribute :>> sourceSheet = "Item";
        attribute :>> sourceRow = 12;
    }
    item trace_86046bf39c648cdd : TraceRecord {
        attribute :>> elementId = "INTERFACETYPE::IF-ACC-008";
        attribute :>> sourceFile = "Rail_MBSE_Function_Interface_v1_final.xlsx";
        attribute :>> sourceSheet = "Item";
        attribute :>> sourceRow = 12;
    }
    item trace_b74e037412182fa1 : TraceRecord {
        attribute :>> elementId = "ITEM::ITM-ACC-009";
        attribute :>> sourceFile = "Rail_MBSE_Function_Interface_v1_final.xlsx";
        attribute :>> sourceSheet = "Item";
        attribute :>> sourceRow = 13;
    }
    item trace_aadb0ee285e4018d : TraceRecord {
        attribute :>> elementId = "PORTTYPE::PT-ACC-009";
        attribute :>> sourceFile = "Rail_MBSE_Function_Interface_v1_final.xlsx";
        attribute :>> sourceSheet = "Item";
        attribute :>> sourceRow = 13;
    }
    item trace_290a5946d25fb1ff : TraceRecord {
        attribute :>> elementId = "INTERFACETYPE::IF-ACC-009";
        attribute :>> sourceFile = "Rail_MBSE_Function_Interface_v1_final.xlsx";
        attribute :>> sourceSheet = "Item";
        attribute :>> sourceRow = 13;
    }
    item trace_75e6167fdb544c6a : TraceRecord {
        attribute :>> elementId = "ITEM::ITM-ACC-010";
        attribute :>> sourceFile = "Rail_MBSE_Function_Interface_v1_final.xlsx";
        attribute :>> sourceSheet = "Item";
        attribute :>> sourceRow = 14;
    }
    item trace_c811f981fd81f95e : TraceRecord {
        attribute :>> elementId = "PORTTYPE::PT-ACC-010";
        attribute :>> sourceFile = "Rail_MBSE_Function_Interface_v1_final.xlsx";
        attribute :>> sourceSheet = "Item";
        attribute :>> sourceRow = 14;
    }
    item trace_4ee2928def5bd81c : TraceRecord {
        attribute :>> elementId = "INTERFACETYPE::IF-ACC-010";
        attribute :>> sourceFile = "Rail_MBSE_Function_Interface_v1_final.xlsx";
        attribute :>> sourceSheet = "Item";
        attribute :>> sourceRow = 14;
    }
    item trace_621b4f3229c0a88d : TraceRecord {
        attribute :>> elementId = "ITEM::ITM-ACC-011";
        attribute :>> sourceFile = "Rail_MBSE_Function_Interface_v1_final.xlsx";
        attribute :>> sourceSheet = "Item";
        attribute :>> sourceRow = 15;
    }
    item trace_a8b611e53acca1ba : TraceRecord {
        attribute :>> elementId = "PORTTYPE::PT-ACC-011";
        attribute :>> sourceFile = "Rail_MBSE_Function_Interface_v1_final.xlsx";
        attribute :>> sourceSheet = "Item";
        attribute :>> sourceRow = 15;
    }
    item trace_1e088762d10fb557 : TraceRecord {
        attribute :>> elementId = "INTERFACETYPE::IF-ACC-011";
        attribute :>> sourceFile = "Rail_MBSE_Function_Interface_v1_final.xlsx";
        attribute :>> sourceSheet = "Item";
        attribute :>> sourceRow = 15;
    }
    item trace_da98663743a761b5 : TraceRecord {
        attribute :>> elementId = "ITEM::ITM-ACC-012";
        attribute :>> sourceFile = "Rail_MBSE_Function_Interface_v1_final.xlsx";
        attribute :>> sourceSheet = "Item";
        attribute :>> sourceRow = 16;
    }
    item trace_a952012517efac0a : TraceRecord {
        attribute :>> elementId = "PORTTYPE::PT-ACC-012";
        attribute :>> sourceFile = "Rail_MBSE_Function_Interface_v1_final.xlsx";
        attribute :>> sourceSheet = "Item";
        attribute :>> sourceRow = 16;
    }
    item trace_e5ff84ad32e72e4f : TraceRecord {
        attribute :>> elementId = "INTERFACETYPE::IF-ACC-012";
        attribute :>> sourceFile = "Rail_MBSE_Function_Interface_v1_final.xlsx";
        attribute :>> sourceSheet = "Item";
        attribute :>> sourceRow = 16;
    }
    item trace_28a5500ec9d564e3 : TraceRecord {
        attribute :>> elementId = "ITEM::ITM-ACC-013";
        attribute :>> sourceFile = "Rail_MBSE_Function_Interface_v1_final.xlsx";
        attribute :>> sourceSheet = "Item";
        attribute :>> sourceRow = 17;
    }
    item trace_742fe22e79ad91c1 : TraceRecord {
        attribute :>> elementId = "PORTTYPE::PT-ACC-013";
        attribute :>> sourceFile = "Rail_MBSE_Function_Interface_v1_final.xlsx";
        attribute :>> sourceSheet = "Item";
        attribute :>> sourceRow = 17;
    }
    item trace_83cd0fab2bed9ef6 : TraceRecord {
        attribute :>> elementId = "INTERFACETYPE::IF-ACC-013";
        attribute :>> sourceFile = "Rail_MBSE_Function_Interface_v1_final.xlsx";
        attribute :>> sourceSheet = "Item";
        attribute :>> sourceRow = 17;
    }
    item trace_2afbd41030026c4c : TraceRecord {
        attribute :>> elementId = "ITEM::ITM-ACC-014";
        attribute :>> sourceFile = "Rail_MBSE_Function_Interface_v1_final.xlsx";
        attribute :>> sourceSheet = "Item";
        attribute :>> sourceRow = 18;
    }
    item trace_abbd763033ef088e : TraceRecord {
        attribute :>> elementId = "PORTTYPE::PT-ACC-014";
        attribute :>> sourceFile = "Rail_MBSE_Function_Interface_v1_final.xlsx";
        attribute :>> sourceSheet = "Item";
        attribute :>> sourceRow = 18;
    }
    item trace_087bf89c35deca2d : TraceRecord {
        attribute :>> elementId = "INTERFACETYPE::IF-ACC-014";
        attribute :>> sourceFile = "Rail_MBSE_Function_Interface_v1_final.xlsx";
        attribute :>> sourceSheet = "Item";
        attribute :>> sourceRow = 18;
    }
    item trace_85e14300ac4dca9a : TraceRecord {
        attribute :>> elementId = "ITEM::ITM-ACC-015";
        attribute :>> sourceFile = "Rail_MBSE_Function_Interface_v1_final.xlsx";
        attribute :>> sourceSheet = "Item";
        attribute :>> sourceRow = 19;
    }
    item trace_5f904d2d385d728b : TraceRecord {
        attribute :>> elementId = "PORTTYPE::PT-ACC-015";
        attribute :>> sourceFile = "Rail_MBSE_Function_Interface_v1_final.xlsx";
        attribute :>> sourceSheet = "Item";
        attribute :>> sourceRow = 19;
    }
    item trace_4af30d3948ce8878 : TraceRecord {
        attribute :>> elementId = "INTERFACETYPE::IF-ACC-015";
        attribute :>> sourceFile = "Rail_MBSE_Function_Interface_v1_final.xlsx";
        attribute :>> sourceSheet = "Item";
        attribute :>> sourceRow = 19;
    }
    item trace_5969c698f196e5a4 : TraceRecord {
        attribute :>> elementId = "ITEM::ITM-CMD-001";
        attribute :>> sourceFile = "Rail_MBSE_Function_Interface_v1_final.xlsx";
        attribute :>> sourceSheet = "Item";
        attribute :>> sourceRow = 20;
    }
    item trace_c27a5c7954e368a4 : TraceRecord {
        attribute :>> elementId = "PORTTYPE::PT-CMD-001";
        attribute :>> sourceFile = "Rail_MBSE_Function_Interface_v1_final.xlsx";
        attribute :>> sourceSheet = "Item";
        attribute :>> sourceRow = 20;
    }
    item trace_844424740f9fbe02 : TraceRecord {
        attribute :>> elementId = "INTERFACETYPE::IF-CMD-001";
        attribute :>> sourceFile = "Rail_MBSE_Function_Interface_v1_final.xlsx";
        attribute :>> sourceSheet = "Item";
        attribute :>> sourceRow = 20;
    }
    item trace_0efea6bf3cc770cf : TraceRecord {
        attribute :>> elementId = "ITEM::ITM-CMD-002";
        attribute :>> sourceFile = "Rail_MBSE_Function_Interface_v1_final.xlsx";
        attribute :>> sourceSheet = "Item";
        attribute :>> sourceRow = 21;
    }
    item trace_0698c9d8dda54126 : TraceRecord {
        attribute :>> elementId = "PORTTYPE::PT-CMD-002";
        attribute :>> sourceFile = "Rail_MBSE_Function_Interface_v1_final.xlsx";
        attribute :>> sourceSheet = "Item";
        attribute :>> sourceRow = 21;
    }
    item trace_2f20b27b17150a21 : TraceRecord {
        attribute :>> elementId = "INTERFACETYPE::IF-CMD-002";
        attribute :>> sourceFile = "Rail_MBSE_Function_Interface_v1_final.xlsx";
        attribute :>> sourceSheet = "Item";
        attribute :>> sourceRow = 21;
    }
    item trace_8978e57861ffeed3 : TraceRecord {
        attribute :>> elementId = "ITEM::ITM-CMD-003";
        attribute :>> sourceFile = "Rail_MBSE_Function_Interface_v1_final.xlsx";
        attribute :>> sourceSheet = "Item";
        attribute :>> sourceRow = 22;
    }
    item trace_e3adc74742b4d86f : TraceRecord {
        attribute :>> elementId = "PORTTYPE::PT-CMD-003";
        attribute :>> sourceFile = "Rail_MBSE_Function_Interface_v1_final.xlsx";
        attribute :>> sourceSheet = "Item";
        attribute :>> sourceRow = 22;
    }
    item trace_ebca511ef5d5ac16 : TraceRecord {
        attribute :>> elementId = "INTERFACETYPE::IF-CMD-003";
        attribute :>> sourceFile = "Rail_MBSE_Function_Interface_v1_final.xlsx";
        attribute :>> sourceSheet = "Item";
        attribute :>> sourceRow = 22;
    }
    item trace_02729ee97db1e3a6 : TraceRecord {
        attribute :>> elementId = "ITEM::ITM-CMD-004";
        attribute :>> sourceFile = "Rail_MBSE_Function_Interface_v1_final.xlsx";
        attribute :>> sourceSheet = "Item";
        attribute :>> sourceRow = 23;
    }
    item trace_e5a63f38c567b9d4 : TraceRecord {
        attribute :>> elementId = "PORTTYPE::PT-CMD-004";
        attribute :>> sourceFile = "Rail_MBSE_Function_Interface_v1_final.xlsx";
        attribute :>> sourceSheet = "Item";
        attribute :>> sourceRow = 23;
    }
    item trace_a3d8cdd9db4c69d6 : TraceRecord {
        attribute :>> elementId = "INTERFACETYPE::IF-CMD-004";
        attribute :>> sourceFile = "Rail_MBSE_Function_Interface_v1_final.xlsx";
        attribute :>> sourceSheet = "Item";
        attribute :>> sourceRow = 23;
    }
    item trace_ad4a7282376dcac8 : TraceRecord {
        attribute :>> elementId = "ITEM::ITM-CMD-005";
        attribute :>> sourceFile = "Rail_MBSE_Function_Interface_v1_final.xlsx";
        attribute :>> sourceSheet = "Item";
        attribute :>> sourceRow = 24;
    }
    item trace_2d693e632b20dd1d : TraceRecord {
        attribute :>> elementId = "PORTTYPE::PT-CMD-005";
        attribute :>> sourceFile = "Rail_MBSE_Function_Interface_v1_final.xlsx";
        attribute :>> sourceSheet = "Item";
        attribute :>> sourceRow = 24;
    }
    item trace_ae2039904a183680 : TraceRecord {
        attribute :>> elementId = "INTERFACETYPE::IF-CMD-005";
        attribute :>> sourceFile = "Rail_MBSE_Function_Interface_v1_final.xlsx";
        attribute :>> sourceSheet = "Item";
        attribute :>> sourceRow = 24;
    }
    item trace_d584a0ed71ec5578 : TraceRecord {
        attribute :>> elementId = "ITEM::ITM-CMD-006";
        attribute :>> sourceFile = "Rail_MBSE_Function_Interface_v1_final.xlsx";
        attribute :>> sourceSheet = "Item";
        attribute :>> sourceRow = 25;
    }
    item trace_fa43822c9ecbac0b : TraceRecord {
        attribute :>> elementId = "PORTTYPE::PT-CMD-006";
        attribute :>> sourceFile = "Rail_MBSE_Function_Interface_v1_final.xlsx";
        attribute :>> sourceSheet = "Item";
        attribute :>> sourceRow = 25;
    }
    item trace_84e99b85e1ae32a6 : TraceRecord {
        attribute :>> elementId = "INTERFACETYPE::IF-CMD-006";
        attribute :>> sourceFile = "Rail_MBSE_Function_Interface_v1_final.xlsx";
        attribute :>> sourceSheet = "Item";
        attribute :>> sourceRow = 25;
    }
    item trace_22cd185799afdd43 : TraceRecord {
        attribute :>> elementId = "ITEM::ITM-CMD-007";
        attribute :>> sourceFile = "Rail_MBSE_Function_Interface_v1_final.xlsx";
        attribute :>> sourceSheet = "Item";
        attribute :>> sourceRow = 26;
    }
    item trace_25ff43942d696961 : TraceRecord {
        attribute :>> elementId = "PORTTYPE::PT-CMD-007";
        attribute :>> sourceFile = "Rail_MBSE_Function_Interface_v1_final.xlsx";
        attribute :>> sourceSheet = "Item";
        attribute :>> sourceRow = 26;
    }
    item trace_4e6679afe12bd112 : TraceRecord {
        attribute :>> elementId = "INTERFACETYPE::IF-CMD-007";
        attribute :>> sourceFile = "Rail_MBSE_Function_Interface_v1_final.xlsx";
        attribute :>> sourceSheet = "Item";
        attribute :>> sourceRow = 26;
    }
    item trace_f524b07b72acb3f3 : TraceRecord {
        attribute :>> elementId = "ITEM::ITM-CMD-008";
        attribute :>> sourceFile = "Rail_MBSE_Function_Interface_v1_final.xlsx";
        attribute :>> sourceSheet = "Item";
        attribute :>> sourceRow = 27;
    }
    item trace_ad359fc3a681b3be : TraceRecord {
        attribute :>> elementId = "PORTTYPE::PT-CMD-008";
        attribute :>> sourceFile = "Rail_MBSE_Function_Interface_v1_final.xlsx";
        attribute :>> sourceSheet = "Item";
        attribute :>> sourceRow = 27;
    }
    item trace_6da6181a9209ff29 : TraceRecord {
        attribute :>> elementId = "INTERFACETYPE::IF-CMD-008";
        attribute :>> sourceFile = "Rail_MBSE_Function_Interface_v1_final.xlsx";
        attribute :>> sourceSheet = "Item";
        attribute :>> sourceRow = 27;
    }
    item trace_b72b89bc764408f8 : TraceRecord {
        attribute :>> elementId = "ITEM::ITM-CMD-009";
        attribute :>> sourceFile = "Rail_MBSE_Function_Interface_v1_final.xlsx";
        attribute :>> sourceSheet = "Item";
        attribute :>> sourceRow = 28;
    }
    item trace_9229c20c50da40b8 : TraceRecord {
        attribute :>> elementId = "PORTTYPE::PT-CMD-009";
        attribute :>> sourceFile = "Rail_MBSE_Function_Interface_v1_final.xlsx";
        attribute :>> sourceSheet = "Item";
        attribute :>> sourceRow = 28;
    }
    item trace_88506dd4ed3fcacb : TraceRecord {
        attribute :>> elementId = "INTERFACETYPE::IF-CMD-009";
        attribute :>> sourceFile = "Rail_MBSE_Function_Interface_v1_final.xlsx";
        attribute :>> sourceSheet = "Item";
        attribute :>> sourceRow = 28;
    }
    item trace_db4201601320deb3 : TraceRecord {
        attribute :>> elementId = "ITEM::ITM-CMD-010";
        attribute :>> sourceFile = "Rail_MBSE_Function_Interface_v1_final.xlsx";
        attribute :>> sourceSheet = "Item";
        attribute :>> sourceRow = 29;
    }
    item trace_2d5f0ed98af47a6e : TraceRecord {
        attribute :>> elementId = "PORTTYPE::PT-CMD-010";
        attribute :>> sourceFile = "Rail_MBSE_Function_Interface_v1_final.xlsx";
        attribute :>> sourceSheet = "Item";
        attribute :>> sourceRow = 29;
    }
    item trace_93fa00a116b61365 : TraceRecord {
        attribute :>> elementId = "INTERFACETYPE::IF-CMD-010";
        attribute :>> sourceFile = "Rail_MBSE_Function_Interface_v1_final.xlsx";
        attribute :>> sourceSheet = "Item";
        attribute :>> sourceRow = 29;
    }
    item trace_f6c1efaf28a956ab : TraceRecord {
        attribute :>> elementId = "ITEM::ITM-CMD-011";
        attribute :>> sourceFile = "Rail_MBSE_Function_Interface_v1_final.xlsx";
        attribute :>> sourceSheet = "Item";
        attribute :>> sourceRow = 30;
    }
    item trace_0fe4f0868be6115a : TraceRecord {
        attribute :>> elementId = "PORTTYPE::PT-CMD-011";
        attribute :>> sourceFile = "Rail_MBSE_Function_Interface_v1_final.xlsx";
        attribute :>> sourceSheet = "Item";
        attribute :>> sourceRow = 30;
    }
    item trace_ba853976dcd07180 : TraceRecord {
        attribute :>> elementId = "INTERFACETYPE::IF-CMD-011";
        attribute :>> sourceFile = "Rail_MBSE_Function_Interface_v1_final.xlsx";
        attribute :>> sourceSheet = "Item";
        attribute :>> sourceRow = 30;
    }
    item trace_290fff13733b99b7 : TraceRecord {
        attribute :>> elementId = "ITEM::ITM-CMD-012";
        attribute :>> sourceFile = "Rail_MBSE_Function_Interface_v1_final.xlsx";
        attribute :>> sourceSheet = "Item";
        attribute :>> sourceRow = 31;
    }
    item trace_7ca14e486f9960da : TraceRecord {
        attribute :>> elementId = "PORTTYPE::PT-CMD-012";
        attribute :>> sourceFile = "Rail_MBSE_Function_Interface_v1_final.xlsx";
        attribute :>> sourceSheet = "Item";
        attribute :>> sourceRow = 31;
    }
    item trace_adef8e74722399cd : TraceRecord {
        attribute :>> elementId = "INTERFACETYPE::IF-CMD-012";
        attribute :>> sourceFile = "Rail_MBSE_Function_Interface_v1_final.xlsx";
        attribute :>> sourceSheet = "Item";
        attribute :>> sourceRow = 31;
    }
    item trace_f46d59d7ce93b5de : TraceRecord {
        attribute :>> elementId = "ITEM::ITM-CMD-013";
        attribute :>> sourceFile = "Rail_MBSE_Function_Interface_v1_final.xlsx";
        attribute :>> sourceSheet = "Item";
        attribute :>> sourceRow = 32;
    }
    item trace_7067413d833151e6 : TraceRecord {
        attribute :>> elementId = "PORTTYPE::PT-CMD-013";
        attribute :>> sourceFile = "Rail_MBSE_Function_Interface_v1_final.xlsx";
        attribute :>> sourceSheet = "Item";
        attribute :>> sourceRow = 32;
    }
    item trace_c10db0beae4b4721 : TraceRecord {
        attribute :>> elementId = "INTERFACETYPE::IF-CMD-013";
        attribute :>> sourceFile = "Rail_MBSE_Function_Interface_v1_final.xlsx";
        attribute :>> sourceSheet = "Item";
        attribute :>> sourceRow = 32;
    }
    item trace_f741a8c85ac34408 : TraceRecord {
        attribute :>> elementId = "ITEM::ITM-CMD-014";
        attribute :>> sourceFile = "Rail_MBSE_Function_Interface_v1_final.xlsx";
        attribute :>> sourceSheet = "Item";
        attribute :>> sourceRow = 33;
    }
    item trace_eb74cbde4f3788f2 : TraceRecord {
        attribute :>> elementId = "PORTTYPE::PT-CMD-014";
        attribute :>> sourceFile = "Rail_MBSE_Function_Interface_v1_final.xlsx";
        attribute :>> sourceSheet = "Item";
        attribute :>> sourceRow = 33;
    }
    item trace_ad29d02e36250178 : TraceRecord {
        attribute :>> elementId = "INTERFACETYPE::IF-CMD-014";
        attribute :>> sourceFile = "Rail_MBSE_Function_Interface_v1_final.xlsx";
        attribute :>> sourceSheet = "Item";
        attribute :>> sourceRow = 33;
    }
    item trace_405596c8fd409be3 : TraceRecord {
        attribute :>> elementId = "ITEM::ITM-CMD-015";
        attribute :>> sourceFile = "Rail_MBSE_Function_Interface_v1_final.xlsx";
        attribute :>> sourceSheet = "Item";
        attribute :>> sourceRow = 34;
    }
    item trace_cfcbb4d2b177ca42 : TraceRecord {
        attribute :>> elementId = "PORTTYPE::PT-CMD-015";
        attribute :>> sourceFile = "Rail_MBSE_Function_Interface_v1_final.xlsx";
        attribute :>> sourceSheet = "Item";
        attribute :>> sourceRow = 34;
    }
    item trace_1bedda0b6549641e : TraceRecord {
        attribute :>> elementId = "INTERFACETYPE::IF-CMD-015";
        attribute :>> sourceFile = "Rail_MBSE_Function_Interface_v1_final.xlsx";
        attribute :>> sourceSheet = "Item";
        attribute :>> sourceRow = 34;
    }
    item trace_33b8a7cfb2663276 : TraceRecord {
        attribute :>> elementId = "ITEM::ITM-CMD-016";
        attribute :>> sourceFile = "Rail_MBSE_Function_Interface_v1_final.xlsx";
        attribute :>> sourceSheet = "Item";
        attribute :>> sourceRow = 35;
    }
    item trace_5ad66c569e6cea02 : TraceRecord {
        attribute :>> elementId = "PORTTYPE::PT-CMD-016";
        attribute :>> sourceFile = "Rail_MBSE_Function_Interface_v1_final.xlsx";
        attribute :>> sourceSheet = "Item";
        attribute :>> sourceRow = 35;
    }
    item trace_430bc05f39705f13 : TraceRecord {
        attribute :>> elementId = "INTERFACETYPE::IF-CMD-016";
        attribute :>> sourceFile = "Rail_MBSE_Function_Interface_v1_final.xlsx";
        attribute :>> sourceSheet = "Item";
        attribute :>> sourceRow = 35;
    }
    item trace_da7b8c620336fd4c : TraceRecord {
        attribute :>> elementId = "ITEM::ITM-CMD-017";
        attribute :>> sourceFile = "Rail_MBSE_Function_Interface_v1_final.xlsx";
        attribute :>> sourceSheet = "Item";
        attribute :>> sourceRow = 36;
    }
    item trace_8cfc9dada48572f1 : TraceRecord {
        attribute :>> elementId = "PORTTYPE::PT-CMD-017";
        attribute :>> sourceFile = "Rail_MBSE_Function_Interface_v1_final.xlsx";
        attribute :>> sourceSheet = "Item";
        attribute :>> sourceRow = 36;
    }
    item trace_0768c10d57ba2f96 : TraceRecord {
        attribute :>> elementId = "INTERFACETYPE::IF-CMD-017";
        attribute :>> sourceFile = "Rail_MBSE_Function_Interface_v1_final.xlsx";
        attribute :>> sourceSheet = "Item";
        attribute :>> sourceRow = 36;
    }
    item trace_fda4173389de7acd : TraceRecord {
        attribute :>> elementId = "ITEM::ITM-CMD-018";
        attribute :>> sourceFile = "Rail_MBSE_Function_Interface_v1_final.xlsx";
        attribute :>> sourceSheet = "Item";
        attribute :>> sourceRow = 37;
    }
    item trace_18121a2e4d7d98bb : TraceRecord {
        attribute :>> elementId = "PORTTYPE::PT-CMD-018";
        attribute :>> sourceFile = "Rail_MBSE_Function_Interface_v1_final.xlsx";
        attribute :>> sourceSheet = "Item";
        attribute :>> sourceRow = 37;
    }
    item trace_32c2a5a73e215e82 : TraceRecord {
        attribute :>> elementId = "INTERFACETYPE::IF-CMD-018";
        attribute :>> sourceFile = "Rail_MBSE_Function_Interface_v1_final.xlsx";
        attribute :>> sourceSheet = "Item";
        attribute :>> sourceRow = 37;
    }
    item trace_3ebc914328c3ef93 : TraceRecord {
        attribute :>> elementId = "ITEM::ITM-CMD-019";
        attribute :>> sourceFile = "Rail_MBSE_Function_Interface_v1_final.xlsx";
        attribute :>> sourceSheet = "Item";
        attribute :>> sourceRow = 38;
    }
    item trace_285ef73dc77f4291 : TraceRecord {
        attribute :>> elementId = "PORTTYPE::PT-CMD-019";
        attribute :>> sourceFile = "Rail_MBSE_Function_Interface_v1_final.xlsx";
        attribute :>> sourceSheet = "Item";
        attribute :>> sourceRow = 38;
    }
    item trace_47581f5bc2fbd922 : TraceRecord {
        attribute :>> elementId = "INTERFACETYPE::IF-CMD-019";
        attribute :>> sourceFile = "Rail_MBSE_Function_Interface_v1_final.xlsx";
        attribute :>> sourceSheet = "Item";
        attribute :>> sourceRow = 38;
    }
    item trace_ba56919a37be75f9 : TraceRecord {
        attribute :>> elementId = "ITEM::ITM-CMD-020";
        attribute :>> sourceFile = "Rail_MBSE_Function_Interface_v1_final.xlsx";
        attribute :>> sourceSheet = "Item";
        attribute :>> sourceRow = 39;
    }
    item trace_055dfe23fcd4ba06 : TraceRecord {
        attribute :>> elementId = "PORTTYPE::PT-CMD-020";
        attribute :>> sourceFile = "Rail_MBSE_Function_Interface_v1_final.xlsx";
        attribute :>> sourceSheet = "Item";
        attribute :>> sourceRow = 39;
    }
    item trace_ae43a44385d035d2 : TraceRecord {
        attribute :>> elementId = "INTERFACETYPE::IF-CMD-020";
        attribute :>> sourceFile = "Rail_MBSE_Function_Interface_v1_final.xlsx";
        attribute :>> sourceSheet = "Item";
        attribute :>> sourceRow = 39;
    }
    item trace_03f65296f6f37c0c : TraceRecord {
        attribute :>> elementId = "ITEM::ITM-CMD-021";
        attribute :>> sourceFile = "Rail_MBSE_Function_Interface_v1_final.xlsx";
        attribute :>> sourceSheet = "Item";
        attribute :>> sourceRow = 40;
    }
    item trace_5c2e4a8c7fceb377 : TraceRecord {
        attribute :>> elementId = "PORTTYPE::PT-CMD-021";
        attribute :>> sourceFile = "Rail_MBSE_Function_Interface_v1_final.xlsx";
        attribute :>> sourceSheet = "Item";
        attribute :>> sourceRow = 40;
    }
    item trace_6a414a3a6e1ffd6c : TraceRecord {
        attribute :>> elementId = "INTERFACETYPE::IF-CMD-021";
        attribute :>> sourceFile = "Rail_MBSE_Function_Interface_v1_final.xlsx";
        attribute :>> sourceSheet = "Item";
        attribute :>> sourceRow = 40;
    }
    item trace_baded99c57be5748 : TraceRecord {
        attribute :>> elementId = "ITEM::ITM-CMD-022";
        attribute :>> sourceFile = "Rail_MBSE_Function_Interface_v1_final.xlsx";
        attribute :>> sourceSheet = "Item";
        attribute :>> sourceRow = 41;
    }
    item trace_98166866d83bf43a : TraceRecord {
        attribute :>> elementId = "PORTTYPE::PT-CMD-022";
        attribute :>> sourceFile = "Rail_MBSE_Function_Interface_v1_final.xlsx";
        attribute :>> sourceSheet = "Item";
        attribute :>> sourceRow = 41;
    }
    item trace_e540ee6cc4043ae3 : TraceRecord {
        attribute :>> elementId = "INTERFACETYPE::IF-CMD-022";
        attribute :>> sourceFile = "Rail_MBSE_Function_Interface_v1_final.xlsx";
        attribute :>> sourceSheet = "Item";
        attribute :>> sourceRow = 41;
    }
    item trace_c8d9afdb81f2bc21 : TraceRecord {
        attribute :>> elementId = "ITEM::ITM-CMD-023";
        attribute :>> sourceFile = "Rail_MBSE_Function_Interface_v1_final.xlsx";
        attribute :>> sourceSheet = "Item";
        attribute :>> sourceRow = 42;
    }
    item trace_3fa6d3b7089c2c9c : TraceRecord {
        attribute :>> elementId = "PORTTYPE::PT-CMD-023";
        attribute :>> sourceFile = "Rail_MBSE_Function_Interface_v1_final.xlsx";
        attribute :>> sourceSheet = "Item";
        attribute :>> sourceRow = 42;
    }
    item trace_d06d6ef580f9e41b : TraceRecord {
        attribute :>> elementId = "INTERFACETYPE::IF-CMD-023";
        attribute :>> sourceFile = "Rail_MBSE_Function_Interface_v1_final.xlsx";
        attribute :>> sourceSheet = "Item";
        attribute :>> sourceRow = 42;
    }
    item trace_7f9c86f812fcce87 : TraceRecord {
        attribute :>> elementId = "ITEM::ITM-CMD-024";
        attribute :>> sourceFile = "Rail_MBSE_Function_Interface_v1_final.xlsx";
        attribute :>> sourceSheet = "Item";
        attribute :>> sourceRow = 43;
    }
    item trace_2d354de2365a63c0 : TraceRecord {
        attribute :>> elementId = "PORTTYPE::PT-CMD-024";
        attribute :>> sourceFile = "Rail_MBSE_Function_Interface_v1_final.xlsx";
        attribute :>> sourceSheet = "Item";
        attribute :>> sourceRow = 43;
    }
    item trace_7234e0be096851c1 : TraceRecord {
        attribute :>> elementId = "INTERFACETYPE::IF-CMD-024";
        attribute :>> sourceFile = "Rail_MBSE_Function_Interface_v1_final.xlsx";
        attribute :>> sourceSheet = "Item";
        attribute :>> sourceRow = 43;
    }
    item trace_bf7be8e76312cfd2 : TraceRecord {
        attribute :>> elementId = "ITEM::ITM-CMD-025";
        attribute :>> sourceFile = "Rail_MBSE_Function_Interface_v1_final.xlsx";
        attribute :>> sourceSheet = "Item";
        attribute :>> sourceRow = 44;
    }
    item trace_f38459b780dafb11 : TraceRecord {
        attribute :>> elementId = "PORTTYPE::PT-CMD-025";
        attribute :>> sourceFile = "Rail_MBSE_Function_Interface_v1_final.xlsx";
        attribute :>> sourceSheet = "Item";
        attribute :>> sourceRow = 44;
    }
    item trace_58d91fac67fe5139 : TraceRecord {
        attribute :>> elementId = "INTERFACETYPE::IF-CMD-025";
        attribute :>> sourceFile = "Rail_MBSE_Function_Interface_v1_final.xlsx";
        attribute :>> sourceSheet = "Item";
        attribute :>> sourceRow = 44;
    }
    item trace_231ca4852791a0b0 : TraceRecord {
        attribute :>> elementId = "ITEM::ITM-CMD-026";
        attribute :>> sourceFile = "Rail_MBSE_Function_Interface_v1_final.xlsx";
        attribute :>> sourceSheet = "Item";
        attribute :>> sourceRow = 45;
    }
    item trace_ade3bb32712506d1 : TraceRecord {
        attribute :>> elementId = "PORTTYPE::PT-CMD-026";
        attribute :>> sourceFile = "Rail_MBSE_Function_Interface_v1_final.xlsx";
        attribute :>> sourceSheet = "Item";
        attribute :>> sourceRow = 45;
    }
    item trace_f54de8a359662943 : TraceRecord {
        attribute :>> elementId = "INTERFACETYPE::IF-CMD-026";
        attribute :>> sourceFile = "Rail_MBSE_Function_Interface_v1_final.xlsx";
        attribute :>> sourceSheet = "Item";
        attribute :>> sourceRow = 45;
    }
    item trace_cee335636edc612c : TraceRecord {
        attribute :>> elementId = "ITEM::ITM-CMD-027";
        attribute :>> sourceFile = "Rail_MBSE_Function_Interface_v1_final.xlsx";
        attribute :>> sourceSheet = "Item";
        attribute :>> sourceRow = 46;
    }
    item trace_7ef72b8b9aab9bc5 : TraceRecord {
        attribute :>> elementId = "PORTTYPE::PT-CMD-027";
        attribute :>> sourceFile = "Rail_MBSE_Function_Interface_v1_final.xlsx";
        attribute :>> sourceSheet = "Item";
        attribute :>> sourceRow = 46;
    }
    item trace_32f4ea04c0937417 : TraceRecord {
        attribute :>> elementId = "INTERFACETYPE::IF-CMD-027";
        attribute :>> sourceFile = "Rail_MBSE_Function_Interface_v1_final.xlsx";
        attribute :>> sourceSheet = "Item";
        attribute :>> sourceRow = 46;
    }
    item trace_56e0d469b7908876 : TraceRecord {
        attribute :>> elementId = "ITEM::ITM-CMD-028";
        attribute :>> sourceFile = "Rail_MBSE_Function_Interface_v1_final.xlsx";
        attribute :>> sourceSheet = "Item";
        attribute :>> sourceRow = 47;
    }
    item trace_dbd50021b1e37088 : TraceRecord {
        attribute :>> elementId = "PORTTYPE::PT-CMD-028";
        attribute :>> sourceFile = "Rail_MBSE_Function_Interface_v1_final.xlsx";
        attribute :>> sourceSheet = "Item";
        attribute :>> sourceRow = 47;
    }
    item trace_8cdf650cb954628b : TraceRecord {
        attribute :>> elementId = "INTERFACETYPE::IF-CMD-028";
        attribute :>> sourceFile = "Rail_MBSE_Function_Interface_v1_final.xlsx";
        attribute :>> sourceSheet = "Item";
        attribute :>> sourceRow = 47;
    }
    item trace_3a855f07add4af83 : TraceRecord {
        attribute :>> elementId = "ITEM::ITM-CMD-029";
        attribute :>> sourceFile = "Rail_MBSE_Function_Interface_v1_final.xlsx";
        attribute :>> sourceSheet = "Item";
        attribute :>> sourceRow = 48;
    }
    item trace_4ddd037f43751f68 : TraceRecord {
        attribute :>> elementId = "PORTTYPE::PT-CMD-029";
        attribute :>> sourceFile = "Rail_MBSE_Function_Interface_v1_final.xlsx";
        attribute :>> sourceSheet = "Item";
        attribute :>> sourceRow = 48;
    }
    item trace_9b47ee3ae18a2321 : TraceRecord {
        attribute :>> elementId = "INTERFACETYPE::IF-CMD-029";
        attribute :>> sourceFile = "Rail_MBSE_Function_Interface_v1_final.xlsx";
        attribute :>> sourceSheet = "Item";
        attribute :>> sourceRow = 48;
    }
    item trace_e674af1470393b6c : TraceRecord {
        attribute :>> elementId = "ITEM::ITM-CMD-030";
        attribute :>> sourceFile = "Rail_MBSE_Function_Interface_v1_final.xlsx";
        attribute :>> sourceSheet = "Item";
        attribute :>> sourceRow = 49;
    }
    item trace_738cb5859c5c75b6 : TraceRecord {
        attribute :>> elementId = "PORTTYPE::PT-CMD-030";
        attribute :>> sourceFile = "Rail_MBSE_Function_Interface_v1_final.xlsx";
        attribute :>> sourceSheet = "Item";
        attribute :>> sourceRow = 49;
    }
    item trace_f25223bc5d418183 : TraceRecord {
        attribute :>> elementId = "INTERFACETYPE::IF-CMD-030";
        attribute :>> sourceFile = "Rail_MBSE_Function_Interface_v1_final.xlsx";
        attribute :>> sourceSheet = "Item";
        attribute :>> sourceRow = 49;
    }
    item trace_e4146ce87a365dcd : TraceRecord {
        attribute :>> elementId = "ITEM::ITM-CMD-031";
        attribute :>> sourceFile = "Rail_MBSE_Function_Interface_v1_final.xlsx";
        attribute :>> sourceSheet = "Item";
        attribute :>> sourceRow = 50;
    }
    item trace_27c6afe71470c4e7 : TraceRecord {
        attribute :>> elementId = "PORTTYPE::PT-CMD-031";
        attribute :>> sourceFile = "Rail_MBSE_Function_Interface_v1_final.xlsx";
        attribute :>> sourceSheet = "Item";
        attribute :>> sourceRow = 50;
    }
    item trace_bfea4aaaff13a1d0 : TraceRecord {
        attribute :>> elementId = "INTERFACETYPE::IF-CMD-031";
        attribute :>> sourceFile = "Rail_MBSE_Function_Interface_v1_final.xlsx";
        attribute :>> sourceSheet = "Item";
        attribute :>> sourceRow = 50;
    }
    item trace_81d009f1df2f0243 : TraceRecord {
        attribute :>> elementId = "ITEM::ITM-CMD-032";
        attribute :>> sourceFile = "Rail_MBSE_Function_Interface_v1_final.xlsx";
        attribute :>> sourceSheet = "Item";
        attribute :>> sourceRow = 51;
    }
    item trace_3e261627e0065d9b : TraceRecord {
        attribute :>> elementId = "PORTTYPE::PT-CMD-032";
        attribute :>> sourceFile = "Rail_MBSE_Function_Interface_v1_final.xlsx";
        attribute :>> sourceSheet = "Item";
        attribute :>> sourceRow = 51;
    }
    item trace_997342343262574a : TraceRecord {
        attribute :>> elementId = "INTERFACETYPE::IF-CMD-032";
        attribute :>> sourceFile = "Rail_MBSE_Function_Interface_v1_final.xlsx";
        attribute :>> sourceSheet = "Item";
        attribute :>> sourceRow = 51;
    }
    item trace_36b0421eafe5f56a : TraceRecord {
        attribute :>> elementId = "ITEM::ITM-LIM-001";
        attribute :>> sourceFile = "Rail_MBSE_Function_Interface_v1_final.xlsx";
        attribute :>> sourceSheet = "Item";
        attribute :>> sourceRow = 52;
    }
    item trace_7512ae1ccbef1ad5 : TraceRecord {
        attribute :>> elementId = "PORTTYPE::PT-LIM-001";
        attribute :>> sourceFile = "Rail_MBSE_Function_Interface_v1_final.xlsx";
        attribute :>> sourceSheet = "Item";
        attribute :>> sourceRow = 52;
    }
    item trace_dd71d6593443d650 : TraceRecord {
        attribute :>> elementId = "INTERFACETYPE::IF-LIM-001";
        attribute :>> sourceFile = "Rail_MBSE_Function_Interface_v1_final.xlsx";
        attribute :>> sourceSheet = "Item";
        attribute :>> sourceRow = 52;
    }
    item trace_ef6612b5741f9a9f : TraceRecord {
        attribute :>> elementId = "ITEM::ITM-LIM-002";
        attribute :>> sourceFile = "Rail_MBSE_Function_Interface_v1_final.xlsx";
        attribute :>> sourceSheet = "Item";
        attribute :>> sourceRow = 53;
    }
    item trace_94780f820b6f98d2 : TraceRecord {
        attribute :>> elementId = "PORTTYPE::PT-LIM-002";
        attribute :>> sourceFile = "Rail_MBSE_Function_Interface_v1_final.xlsx";
        attribute :>> sourceSheet = "Item";
        attribute :>> sourceRow = 53;
    }
    item trace_992200f7810e5918 : TraceRecord {
        attribute :>> elementId = "INTERFACETYPE::IF-LIM-002";
        attribute :>> sourceFile = "Rail_MBSE_Function_Interface_v1_final.xlsx";
        attribute :>> sourceSheet = "Item";
        attribute :>> sourceRow = 53;
    }
    item trace_29cd48aa61cc73c1 : TraceRecord {
        attribute :>> elementId = "ITEM::ITM-LIM-003";
        attribute :>> sourceFile = "Rail_MBSE_Function_Interface_v1_final.xlsx";
        attribute :>> sourceSheet = "Item";
        attribute :>> sourceRow = 54;
    }
    item trace_71c24aef930a54bf : TraceRecord {
        attribute :>> elementId = "PORTTYPE::PT-LIM-003";
        attribute :>> sourceFile = "Rail_MBSE_Function_Interface_v1_final.xlsx";
        attribute :>> sourceSheet = "Item";
        attribute :>> sourceRow = 54;
    }
    item trace_fd2c8ce079ca2a8c : TraceRecord {
        attribute :>> elementId = "INTERFACETYPE::IF-LIM-003";
        attribute :>> sourceFile = "Rail_MBSE_Function_Interface_v1_final.xlsx";
        attribute :>> sourceSheet = "Item";
        attribute :>> sourceRow = 54;
    }
    item trace_7a158f74a03f203f : TraceRecord {
        attribute :>> elementId = "ITEM::ITM-LIM-004";
        attribute :>> sourceFile = "Rail_MBSE_Function_Interface_v1_final.xlsx";
        attribute :>> sourceSheet = "Item";
        attribute :>> sourceRow = 55;
    }
    item trace_c790495304ef3e00 : TraceRecord {
        attribute :>> elementId = "PORTTYPE::PT-LIM-004";
        attribute :>> sourceFile = "Rail_MBSE_Function_Interface_v1_final.xlsx";
        attribute :>> sourceSheet = "Item";
        attribute :>> sourceRow = 55;
    }
    item trace_b03ac13c9f46fd10 : TraceRecord {
        attribute :>> elementId = "INTERFACETYPE::IF-LIM-004";
        attribute :>> sourceFile = "Rail_MBSE_Function_Interface_v1_final.xlsx";
        attribute :>> sourceSheet = "Item";
        attribute :>> sourceRow = 55;
    }
    item trace_8ab2a1acc3c703d2 : TraceRecord {
        attribute :>> elementId = "ITEM::ITM-LIM-005";
        attribute :>> sourceFile = "Rail_MBSE_Function_Interface_v1_final.xlsx";
        attribute :>> sourceSheet = "Item";
        attribute :>> sourceRow = 56;
    }
    item trace_ee3c7c3bfccb066c : TraceRecord {
        attribute :>> elementId = "PORTTYPE::PT-LIM-005";
        attribute :>> sourceFile = "Rail_MBSE_Function_Interface_v1_final.xlsx";
        attribute :>> sourceSheet = "Item";
        attribute :>> sourceRow = 56;
    }
    item trace_8a38f7fe146e0122 : TraceRecord {
        attribute :>> elementId = "INTERFACETYPE::IF-LIM-005";
        attribute :>> sourceFile = "Rail_MBSE_Function_Interface_v1_final.xlsx";
        attribute :>> sourceSheet = "Item";
        attribute :>> sourceRow = 56;
    }
    item trace_384fa6d01049d4e6 : TraceRecord {
        attribute :>> elementId = "ITEM::ITM-LIM-006";
        attribute :>> sourceFile = "Rail_MBSE_Function_Interface_v1_final.xlsx";
        attribute :>> sourceSheet = "Item";
        attribute :>> sourceRow = 57;
    }
    item trace_8dfcc86009be0736 : TraceRecord {
        attribute :>> elementId = "PORTTYPE::PT-LIM-006";
        attribute :>> sourceFile = "Rail_MBSE_Function_Interface_v1_final.xlsx";
        attribute :>> sourceSheet = "Item";
        attribute :>> sourceRow = 57;
    }
    item trace_92adbb3e720c3e0f : TraceRecord {
        attribute :>> elementId = "INTERFACETYPE::IF-LIM-006";
        attribute :>> sourceFile = "Rail_MBSE_Function_Interface_v1_final.xlsx";
        attribute :>> sourceSheet = "Item";
        attribute :>> sourceRow = 57;
    }
    item trace_6dcb42cd183f5a92 : TraceRecord {
        attribute :>> elementId = "ITEM::ITM-LIM-007";
        attribute :>> sourceFile = "Rail_MBSE_Function_Interface_v1_final.xlsx";
        attribute :>> sourceSheet = "Item";
        attribute :>> sourceRow = 58;
    }
    item trace_b050685b5f199d95 : TraceRecord {
        attribute :>> elementId = "PORTTYPE::PT-LIM-007";
        attribute :>> sourceFile = "Rail_MBSE_Function_Interface_v1_final.xlsx";
        attribute :>> sourceSheet = "Item";
        attribute :>> sourceRow = 58;
    }
    item trace_a4f33f09ed550060 : TraceRecord {
        attribute :>> elementId = "INTERFACETYPE::IF-LIM-007";
        attribute :>> sourceFile = "Rail_MBSE_Function_Interface_v1_final.xlsx";
        attribute :>> sourceSheet = "Item";
        attribute :>> sourceRow = 58;
    }
    item trace_2c51e0c892027400 : TraceRecord {
        attribute :>> elementId = "ITEM::ITM-LIM-008";
        attribute :>> sourceFile = "Rail_MBSE_Function_Interface_v1_final.xlsx";
        attribute :>> sourceSheet = "Item";
        attribute :>> sourceRow = 59;
    }
    item trace_16d7b576b1180e39 : TraceRecord {
        attribute :>> elementId = "PORTTYPE::PT-LIM-008";
        attribute :>> sourceFile = "Rail_MBSE_Function_Interface_v1_final.xlsx";
        attribute :>> sourceSheet = "Item";
        attribute :>> sourceRow = 59;
    }
    item trace_9612657e4b5371da : TraceRecord {
        attribute :>> elementId = "INTERFACETYPE::IF-LIM-008";
        attribute :>> sourceFile = "Rail_MBSE_Function_Interface_v1_final.xlsx";
        attribute :>> sourceSheet = "Item";
        attribute :>> sourceRow = 59;
    }
    item trace_46cd77bfb449c081 : TraceRecord {
        attribute :>> elementId = "ITEM::ITM-LIM-009";
        attribute :>> sourceFile = "Rail_MBSE_Function_Interface_v1_final.xlsx";
        attribute :>> sourceSheet = "Item";
        attribute :>> sourceRow = 60;
    }
    item trace_e05712e685197bc1 : TraceRecord {
        attribute :>> elementId = "PORTTYPE::PT-LIM-009";
        attribute :>> sourceFile = "Rail_MBSE_Function_Interface_v1_final.xlsx";
        attribute :>> sourceSheet = "Item";
        attribute :>> sourceRow = 60;
    }
    item trace_46da4958949cfd02 : TraceRecord {
        attribute :>> elementId = "INTERFACETYPE::IF-LIM-009";
        attribute :>> sourceFile = "Rail_MBSE_Function_Interface_v1_final.xlsx";
        attribute :>> sourceSheet = "Item";
        attribute :>> sourceRow = 60;
    }
    item trace_b3056294877ba608 : TraceRecord {
        attribute :>> elementId = "ITEM::ITM-LIM-010";
        attribute :>> sourceFile = "Rail_MBSE_Function_Interface_v1_final.xlsx";
        attribute :>> sourceSheet = "Item";
        attribute :>> sourceRow = 61;
    }
    item trace_9f0e9e7a87847503 : TraceRecord {
        attribute :>> elementId = "PORTTYPE::PT-LIM-010";
        attribute :>> sourceFile = "Rail_MBSE_Function_Interface_v1_final.xlsx";
        attribute :>> sourceSheet = "Item";
        attribute :>> sourceRow = 61;
    }
    item trace_72f28557929278d0 : TraceRecord {
        attribute :>> elementId = "INTERFACETYPE::IF-LIM-010";
        attribute :>> sourceFile = "Rail_MBSE_Function_Interface_v1_final.xlsx";
        attribute :>> sourceSheet = "Item";
        attribute :>> sourceRow = 61;
    }
    item trace_3e7448beed819572 : TraceRecord {
        attribute :>> elementId = "ITEM::ITM-LIM-011";
        attribute :>> sourceFile = "Rail_MBSE_Function_Interface_v1_final.xlsx";
        attribute :>> sourceSheet = "Item";
        attribute :>> sourceRow = 62;
    }
    item trace_fd6a3741f0694727 : TraceRecord {
        attribute :>> elementId = "PORTTYPE::PT-LIM-011";
        attribute :>> sourceFile = "Rail_MBSE_Function_Interface_v1_final.xlsx";
        attribute :>> sourceSheet = "Item";
        attribute :>> sourceRow = 62;
    }
    item trace_67a458e6a1b70399 : TraceRecord {
        attribute :>> elementId = "INTERFACETYPE::IF-LIM-011";
        attribute :>> sourceFile = "Rail_MBSE_Function_Interface_v1_final.xlsx";
        attribute :>> sourceSheet = "Item";
        attribute :>> sourceRow = 62;
    }
    item trace_4bae55df679202a2 : TraceRecord {
        attribute :>> elementId = "ITEM::ITM-LIM-012";
        attribute :>> sourceFile = "Rail_MBSE_Function_Interface_v1_final.xlsx";
        attribute :>> sourceSheet = "Item";
        attribute :>> sourceRow = 63;
    }
    item trace_7459dd754b5b20aa : TraceRecord {
        attribute :>> elementId = "PORTTYPE::PT-LIM-012";
        attribute :>> sourceFile = "Rail_MBSE_Function_Interface_v1_final.xlsx";
        attribute :>> sourceSheet = "Item";
        attribute :>> sourceRow = 63;
    }
    item trace_cfd4ff2a03ca945e : TraceRecord {
        attribute :>> elementId = "INTERFACETYPE::IF-LIM-012";
        attribute :>> sourceFile = "Rail_MBSE_Function_Interface_v1_final.xlsx";
        attribute :>> sourceSheet = "Item";
        attribute :>> sourceRow = 63;
    }
    item trace_ea9365b60aad5f97 : TraceRecord {
        attribute :>> elementId = "ITEM::ITM-LIM-013";
        attribute :>> sourceFile = "Rail_MBSE_Function_Interface_v1_final.xlsx";
        attribute :>> sourceSheet = "Item";
        attribute :>> sourceRow = 64;
    }
    item trace_60566ee4e5d1284a : TraceRecord {
        attribute :>> elementId = "PORTTYPE::PT-LIM-013";
        attribute :>> sourceFile = "Rail_MBSE_Function_Interface_v1_final.xlsx";
        attribute :>> sourceSheet = "Item";
        attribute :>> sourceRow = 64;
    }
    item trace_b78461dc420a4577 : TraceRecord {
        attribute :>> elementId = "INTERFACETYPE::IF-LIM-013";
        attribute :>> sourceFile = "Rail_MBSE_Function_Interface_v1_final.xlsx";
        attribute :>> sourceSheet = "Item";
        attribute :>> sourceRow = 64;
    }
    item trace_622b66b2c1bbf5cb : TraceRecord {
        attribute :>> elementId = "ITEM::ITM-LIM-014";
        attribute :>> sourceFile = "Rail_MBSE_Function_Interface_v1_final.xlsx";
        attribute :>> sourceSheet = "Item";
        attribute :>> sourceRow = 65;
    }
    item trace_a207917f9b9188ee : TraceRecord {
        attribute :>> elementId = "PORTTYPE::PT-LIM-014";
        attribute :>> sourceFile = "Rail_MBSE_Function_Interface_v1_final.xlsx";
        attribute :>> sourceSheet = "Item";
        attribute :>> sourceRow = 65;
    }
    item trace_24f17d51657ca138 : TraceRecord {
        attribute :>> elementId = "INTERFACETYPE::IF-LIM-014";
        attribute :>> sourceFile = "Rail_MBSE_Function_Interface_v1_final.xlsx";
        attribute :>> sourceSheet = "Item";
        attribute :>> sourceRow = 65;
    }
    item trace_ffaa6cefc256ff06 : TraceRecord {
        attribute :>> elementId = "ITEM::ITM-MEA-001";
        attribute :>> sourceFile = "Rail_MBSE_Function_Interface_v1_final.xlsx";
        attribute :>> sourceSheet = "Item";
        attribute :>> sourceRow = 66;
    }
    item trace_b8f8d27edb6695f9 : TraceRecord {
        attribute :>> elementId = "PORTTYPE::PT-MEA-001";
        attribute :>> sourceFile = "Rail_MBSE_Function_Interface_v1_final.xlsx";
        attribute :>> sourceSheet = "Item";
        attribute :>> sourceRow = 66;
    }
    item trace_9cdfb6c62ce15fb4 : TraceRecord {
        attribute :>> elementId = "INTERFACETYPE::IF-MEA-001";
        attribute :>> sourceFile = "Rail_MBSE_Function_Interface_v1_final.xlsx";
        attribute :>> sourceSheet = "Item";
        attribute :>> sourceRow = 66;
    }
    item trace_851d285088d9c305 : TraceRecord {
        attribute :>> elementId = "ITEM::ITM-MEA-002";
        attribute :>> sourceFile = "Rail_MBSE_Function_Interface_v1_final.xlsx";
        attribute :>> sourceSheet = "Item";
        attribute :>> sourceRow = 67;
    }
    item trace_6973d718f5edfca5 : TraceRecord {
        attribute :>> elementId = "PORTTYPE::PT-MEA-002";
        attribute :>> sourceFile = "Rail_MBSE_Function_Interface_v1_final.xlsx";
        attribute :>> sourceSheet = "Item";
        attribute :>> sourceRow = 67;
    }
    item trace_ca7325a4038f79e9 : TraceRecord {
        attribute :>> elementId = "INTERFACETYPE::IF-MEA-002";
        attribute :>> sourceFile = "Rail_MBSE_Function_Interface_v1_final.xlsx";
        attribute :>> sourceSheet = "Item";
        attribute :>> sourceRow = 67;
    }
    item trace_a2f85e4f0349df2f : TraceRecord {
        attribute :>> elementId = "ITEM::ITM-MEA-003";
        attribute :>> sourceFile = "Rail_MBSE_Function_Interface_v1_final.xlsx";
        attribute :>> sourceSheet = "Item";
        attribute :>> sourceRow = 68;
    }
    item trace_e90a6b4f766290c9 : TraceRecord {
        attribute :>> elementId = "PORTTYPE::PT-MEA-003";
        attribute :>> sourceFile = "Rail_MBSE_Function_Interface_v1_final.xlsx";
        attribute :>> sourceSheet = "Item";
        attribute :>> sourceRow = 68;
    }
    item trace_535a66bd6e2e2408 : TraceRecord {
        attribute :>> elementId = "INTERFACETYPE::IF-MEA-003";
        attribute :>> sourceFile = "Rail_MBSE_Function_Interface_v1_final.xlsx";
        attribute :>> sourceSheet = "Item";
        attribute :>> sourceRow = 68;
    }
    item trace_f6ab3c2e7f436449 : TraceRecord {
        attribute :>> elementId = "ITEM::ITM-MEA-004";
        attribute :>> sourceFile = "Rail_MBSE_Function_Interface_v1_final.xlsx";
        attribute :>> sourceSheet = "Item";
        attribute :>> sourceRow = 69;
    }
    item trace_8594194ac447a8ec : TraceRecord {
        attribute :>> elementId = "PORTTYPE::PT-MEA-004";
        attribute :>> sourceFile = "Rail_MBSE_Function_Interface_v1_final.xlsx";
        attribute :>> sourceSheet = "Item";
        attribute :>> sourceRow = 69;
    }
    item trace_a1e1c2f02070a8b2 : TraceRecord {
        attribute :>> elementId = "INTERFACETYPE::IF-MEA-004";
        attribute :>> sourceFile = "Rail_MBSE_Function_Interface_v1_final.xlsx";
        attribute :>> sourceSheet = "Item";
        attribute :>> sourceRow = 69;
    }
    item trace_f6c65311def3196c : TraceRecord {
        attribute :>> elementId = "ITEM::ITM-MEA-005";
        attribute :>> sourceFile = "Rail_MBSE_Function_Interface_v1_final.xlsx";
        attribute :>> sourceSheet = "Item";
        attribute :>> sourceRow = 70;
    }
    item trace_8e28285d70e6d044 : TraceRecord {
        attribute :>> elementId = "PORTTYPE::PT-MEA-005";
        attribute :>> sourceFile = "Rail_MBSE_Function_Interface_v1_final.xlsx";
        attribute :>> sourceSheet = "Item";
        attribute :>> sourceRow = 70;
    }
    item trace_92fa5be95dff17e7 : TraceRecord {
        attribute :>> elementId = "INTERFACETYPE::IF-MEA-005";
        attribute :>> sourceFile = "Rail_MBSE_Function_Interface_v1_final.xlsx";
        attribute :>> sourceSheet = "Item";
        attribute :>> sourceRow = 70;
    }
    item trace_658ac1afae1672f5 : TraceRecord {
        attribute :>> elementId = "ITEM::ITM-MEA-006";
        attribute :>> sourceFile = "Rail_MBSE_Function_Interface_v1_final.xlsx";
        attribute :>> sourceSheet = "Item";
        attribute :>> sourceRow = 71;
    }
    item trace_fe9d6ac010b90ffe : TraceRecord {
        attribute :>> elementId = "PORTTYPE::PT-MEA-006";
        attribute :>> sourceFile = "Rail_MBSE_Function_Interface_v1_final.xlsx";
        attribute :>> sourceSheet = "Item";
        attribute :>> sourceRow = 71;
    }
    item trace_56a3d02a3bca64f3 : TraceRecord {
        attribute :>> elementId = "INTERFACETYPE::IF-MEA-006";
        attribute :>> sourceFile = "Rail_MBSE_Function_Interface_v1_final.xlsx";
        attribute :>> sourceSheet = "Item";
        attribute :>> sourceRow = 71;
    }
    item trace_fe42d984d793f208 : TraceRecord {
        attribute :>> elementId = "ITEM::ITM-MEA-007";
        attribute :>> sourceFile = "Rail_MBSE_Function_Interface_v1_final.xlsx";
        attribute :>> sourceSheet = "Item";
        attribute :>> sourceRow = 72;
    }
    item trace_ac2414d91d7d50f4 : TraceRecord {
        attribute :>> elementId = "PORTTYPE::PT-MEA-007";
        attribute :>> sourceFile = "Rail_MBSE_Function_Interface_v1_final.xlsx";
        attribute :>> sourceSheet = "Item";
        attribute :>> sourceRow = 72;
    }
    item trace_9a65f94c07357f73 : TraceRecord {
        attribute :>> elementId = "INTERFACETYPE::IF-MEA-007";
        attribute :>> sourceFile = "Rail_MBSE_Function_Interface_v1_final.xlsx";
        attribute :>> sourceSheet = "Item";
        attribute :>> sourceRow = 72;
    }
    item trace_f10d4e63c1248a55 : TraceRecord {
        attribute :>> elementId = "ITEM::ITM-MEA-008";
        attribute :>> sourceFile = "Rail_MBSE_Function_Interface_v1_final.xlsx";
        attribute :>> sourceSheet = "Item";
        attribute :>> sourceRow = 73;
    }
    item trace_1fc2247686fdd06e : TraceRecord {
        attribute :>> elementId = "PORTTYPE::PT-MEA-008";
        attribute :>> sourceFile = "Rail_MBSE_Function_Interface_v1_final.xlsx";
        attribute :>> sourceSheet = "Item";
        attribute :>> sourceRow = 73;
    }
    item trace_337181ba66ddcb25 : TraceRecord {
        attribute :>> elementId = "INTERFACETYPE::IF-MEA-008";
        attribute :>> sourceFile = "Rail_MBSE_Function_Interface_v1_final.xlsx";
        attribute :>> sourceSheet = "Item";
        attribute :>> sourceRow = 73;
    }
    item trace_ccba761e6c2a0a0a : TraceRecord {
        attribute :>> elementId = "ITEM::ITM-MEA-009";
        attribute :>> sourceFile = "Rail_MBSE_Function_Interface_v1_final.xlsx";
        attribute :>> sourceSheet = "Item";
        attribute :>> sourceRow = 74;
    }
    item trace_718ec4d97dc73ff1 : TraceRecord {
        attribute :>> elementId = "PORTTYPE::PT-MEA-009";
        attribute :>> sourceFile = "Rail_MBSE_Function_Interface_v1_final.xlsx";
        attribute :>> sourceSheet = "Item";
        attribute :>> sourceRow = 74;
    }
    item trace_e15fb3eca24051b4 : TraceRecord {
        attribute :>> elementId = "INTERFACETYPE::IF-MEA-009";
        attribute :>> sourceFile = "Rail_MBSE_Function_Interface_v1_final.xlsx";
        attribute :>> sourceSheet = "Item";
        attribute :>> sourceRow = 74;
    }
    item trace_8c78b73266e61796 : TraceRecord {
        attribute :>> elementId = "ITEM::ITM-MEA-010";
        attribute :>> sourceFile = "Rail_MBSE_Function_Interface_v1_final.xlsx";
        attribute :>> sourceSheet = "Item";
        attribute :>> sourceRow = 75;
    }
    item trace_70b71ac6f0f1f0f9 : TraceRecord {
        attribute :>> elementId = "PORTTYPE::PT-MEA-010";
        attribute :>> sourceFile = "Rail_MBSE_Function_Interface_v1_final.xlsx";
        attribute :>> sourceSheet = "Item";
        attribute :>> sourceRow = 75;
    }
    item trace_91b906dca815a238 : TraceRecord {
        attribute :>> elementId = "INTERFACETYPE::IF-MEA-010";
        attribute :>> sourceFile = "Rail_MBSE_Function_Interface_v1_final.xlsx";
        attribute :>> sourceSheet = "Item";
        attribute :>> sourceRow = 75;
    }
    item trace_7a255360c4c76059 : TraceRecord {
        attribute :>> elementId = "ITEM::ITM-MEA-011";
        attribute :>> sourceFile = "Rail_MBSE_Function_Interface_v1_final.xlsx";
        attribute :>> sourceSheet = "Item";
        attribute :>> sourceRow = 76;
    }
    item trace_0d36e1f5ee4781cc : TraceRecord {
        attribute :>> elementId = "PORTTYPE::PT-MEA-011";
        attribute :>> sourceFile = "Rail_MBSE_Function_Interface_v1_final.xlsx";
        attribute :>> sourceSheet = "Item";
        attribute :>> sourceRow = 76;
    }
    item trace_a8bfb08fa3905223 : TraceRecord {
        attribute :>> elementId = "INTERFACETYPE::IF-MEA-011";
        attribute :>> sourceFile = "Rail_MBSE_Function_Interface_v1_final.xlsx";
        attribute :>> sourceSheet = "Item";
        attribute :>> sourceRow = 76;
    }
    item trace_5fc8e9b0d634d118 : TraceRecord {
        attribute :>> elementId = "ITEM::ITM-MEA-012";
        attribute :>> sourceFile = "Rail_MBSE_Function_Interface_v1_final.xlsx";
        attribute :>> sourceSheet = "Item";
        attribute :>> sourceRow = 77;
    }
    item trace_51658f9ed53c3dc5 : TraceRecord {
        attribute :>> elementId = "PORTTYPE::PT-MEA-012";
        attribute :>> sourceFile = "Rail_MBSE_Function_Interface_v1_final.xlsx";
        attribute :>> sourceSheet = "Item";
        attribute :>> sourceRow = 77;
    }
    item trace_abdb0835550a607a : TraceRecord {
        attribute :>> elementId = "INTERFACETYPE::IF-MEA-012";
        attribute :>> sourceFile = "Rail_MBSE_Function_Interface_v1_final.xlsx";
        attribute :>> sourceSheet = "Item";
        attribute :>> sourceRow = 77;
    }
    item trace_fef5e676d691168c : TraceRecord {
        attribute :>> elementId = "ITEM::ITM-MEA-013";
        attribute :>> sourceFile = "Rail_MBSE_Function_Interface_v1_final.xlsx";
        attribute :>> sourceSheet = "Item";
        attribute :>> sourceRow = 78;
    }
    item trace_7d4ed4d556b2228c : TraceRecord {
        attribute :>> elementId = "PORTTYPE::PT-MEA-013";
        attribute :>> sourceFile = "Rail_MBSE_Function_Interface_v1_final.xlsx";
        attribute :>> sourceSheet = "Item";
        attribute :>> sourceRow = 78;
    }
    item trace_af66f28004e74fd0 : TraceRecord {
        attribute :>> elementId = "INTERFACETYPE::IF-MEA-013";
        attribute :>> sourceFile = "Rail_MBSE_Function_Interface_v1_final.xlsx";
        attribute :>> sourceSheet = "Item";
        attribute :>> sourceRow = 78;
    }
    item trace_4f916e4f51c5f41a : TraceRecord {
        attribute :>> elementId = "ITEM::ITM-MEA-014";
        attribute :>> sourceFile = "Rail_MBSE_Function_Interface_v1_final.xlsx";
        attribute :>> sourceSheet = "Item";
        attribute :>> sourceRow = 79;
    }
    item trace_2cd7f2c25a7dd0b6 : TraceRecord {
        attribute :>> elementId = "PORTTYPE::PT-MEA-014";
        attribute :>> sourceFile = "Rail_MBSE_Function_Interface_v1_final.xlsx";
        attribute :>> sourceSheet = "Item";
        attribute :>> sourceRow = 79;
    }
    item trace_b6128509d551aa24 : TraceRecord {
        attribute :>> elementId = "INTERFACETYPE::IF-MEA-014";
        attribute :>> sourceFile = "Rail_MBSE_Function_Interface_v1_final.xlsx";
        attribute :>> sourceSheet = "Item";
        attribute :>> sourceRow = 79;
    }
    item trace_7ce5a0090d29a6e0 : TraceRecord {
        attribute :>> elementId = "ITEM::ITM-MEA-015";
        attribute :>> sourceFile = "Rail_MBSE_Function_Interface_v1_final.xlsx";
        attribute :>> sourceSheet = "Item";
        attribute :>> sourceRow = 80;
    }
    item trace_611834f4f85aa8d5 : TraceRecord {
        attribute :>> elementId = "PORTTYPE::PT-MEA-015";
        attribute :>> sourceFile = "Rail_MBSE_Function_Interface_v1_final.xlsx";
        attribute :>> sourceSheet = "Item";
        attribute :>> sourceRow = 80;
    }
    item trace_bee2a7e2861587e0 : TraceRecord {
        attribute :>> elementId = "INTERFACETYPE::IF-MEA-015";
        attribute :>> sourceFile = "Rail_MBSE_Function_Interface_v1_final.xlsx";
        attribute :>> sourceSheet = "Item";
        attribute :>> sourceRow = 80;
    }
    item trace_492dc863162a011f : TraceRecord {
        attribute :>> elementId = "ITEM::ITM-MEA-016";
        attribute :>> sourceFile = "Rail_MBSE_Function_Interface_v1_final.xlsx";
        attribute :>> sourceSheet = "Item";
        attribute :>> sourceRow = 81;
    }
    item trace_fbb982dccd6a9cb1 : TraceRecord {
        attribute :>> elementId = "PORTTYPE::PT-MEA-016";
        attribute :>> sourceFile = "Rail_MBSE_Function_Interface_v1_final.xlsx";
        attribute :>> sourceSheet = "Item";
        attribute :>> sourceRow = 81;
    }
    item trace_13c9abc319b62af9 : TraceRecord {
        attribute :>> elementId = "INTERFACETYPE::IF-MEA-016";
        attribute :>> sourceFile = "Rail_MBSE_Function_Interface_v1_final.xlsx";
        attribute :>> sourceSheet = "Item";
        attribute :>> sourceRow = 81;
    }
    item trace_b00904c7e2385319 : TraceRecord {
        attribute :>> elementId = "ITEM::ITM-MEA-017";
        attribute :>> sourceFile = "Rail_MBSE_Function_Interface_v1_final.xlsx";
        attribute :>> sourceSheet = "Item";
        attribute :>> sourceRow = 82;
    }
    item trace_73f774ef89191df9 : TraceRecord {
        attribute :>> elementId = "PORTTYPE::PT-MEA-017";
        attribute :>> sourceFile = "Rail_MBSE_Function_Interface_v1_final.xlsx";
        attribute :>> sourceSheet = "Item";
        attribute :>> sourceRow = 82;
    }
    item trace_f18d0839aa323466 : TraceRecord {
        attribute :>> elementId = "INTERFACETYPE::IF-MEA-017";
        attribute :>> sourceFile = "Rail_MBSE_Function_Interface_v1_final.xlsx";
        attribute :>> sourceSheet = "Item";
        attribute :>> sourceRow = 82;
    }
    item trace_104e91c6d3ebfcb9 : TraceRecord {
        attribute :>> elementId = "ITEM::ITM-MEA-018";
        attribute :>> sourceFile = "Rail_MBSE_Function_Interface_v1_final.xlsx";
        attribute :>> sourceSheet = "Item";
        attribute :>> sourceRow = 83;
    }
    item trace_6637d93c6e2b15b9 : TraceRecord {
        attribute :>> elementId = "PORTTYPE::PT-MEA-018";
        attribute :>> sourceFile = "Rail_MBSE_Function_Interface_v1_final.xlsx";
        attribute :>> sourceSheet = "Item";
        attribute :>> sourceRow = 83;
    }
    item trace_29cb784e07630fad : TraceRecord {
        attribute :>> elementId = "INTERFACETYPE::IF-MEA-018";
        attribute :>> sourceFile = "Rail_MBSE_Function_Interface_v1_final.xlsx";
        attribute :>> sourceSheet = "Item";
        attribute :>> sourceRow = 83;
    }
    item trace_89b065f0ac6e076d : TraceRecord {
        attribute :>> elementId = "ITEM::ITM-MEA-019";
        attribute :>> sourceFile = "Rail_MBSE_Function_Interface_v1_final.xlsx";
        attribute :>> sourceSheet = "Item";
        attribute :>> sourceRow = 84;
    }
    item trace_2d2539df1b0cabe3 : TraceRecord {
        attribute :>> elementId = "PORTTYPE::PT-MEA-019";
        attribute :>> sourceFile = "Rail_MBSE_Function_Interface_v1_final.xlsx";
        attribute :>> sourceSheet = "Item";
        attribute :>> sourceRow = 84;
    }
    item trace_5eb1200dd95d54e1 : TraceRecord {
        attribute :>> elementId = "INTERFACETYPE::IF-MEA-019";
        attribute :>> sourceFile = "Rail_MBSE_Function_Interface_v1_final.xlsx";
        attribute :>> sourceSheet = "Item";
        attribute :>> sourceRow = 84;
    }
    item trace_869f39c31b30b677 : TraceRecord {
        attribute :>> elementId = "ITEM::ITM-MEA-020";
        attribute :>> sourceFile = "Rail_MBSE_Function_Interface_v1_final.xlsx";
        attribute :>> sourceSheet = "Item";
        attribute :>> sourceRow = 85;
    }
    item trace_14c9bbe65c3b72df : TraceRecord {
        attribute :>> elementId = "PORTTYPE::PT-MEA-020";
        attribute :>> sourceFile = "Rail_MBSE_Function_Interface_v1_final.xlsx";
        attribute :>> sourceSheet = "Item";
        attribute :>> sourceRow = 85;
    }
    item trace_ad901794ed388551 : TraceRecord {
        attribute :>> elementId = "INTERFACETYPE::IF-MEA-020";
        attribute :>> sourceFile = "Rail_MBSE_Function_Interface_v1_final.xlsx";
        attribute :>> sourceSheet = "Item";
        attribute :>> sourceRow = 85;
    }
    item trace_006e4ce84fa05645 : TraceRecord {
        attribute :>> elementId = "ITEM::ITM-MEA-021";
        attribute :>> sourceFile = "Rail_MBSE_Function_Interface_v1_final.xlsx";
        attribute :>> sourceSheet = "Item";
        attribute :>> sourceRow = 86;
    }
    item trace_4ddbe853210c87ba : TraceRecord {
        attribute :>> elementId = "PORTTYPE::PT-MEA-021";
        attribute :>> sourceFile = "Rail_MBSE_Function_Interface_v1_final.xlsx";
        attribute :>> sourceSheet = "Item";
        attribute :>> sourceRow = 86;
    }
    item trace_e2d09926d3d1c555 : TraceRecord {
        attribute :>> elementId = "INTERFACETYPE::IF-MEA-021";
        attribute :>> sourceFile = "Rail_MBSE_Function_Interface_v1_final.xlsx";
        attribute :>> sourceSheet = "Item";
        attribute :>> sourceRow = 86;
    }
    item trace_baeaeb5c2196b4d5 : TraceRecord {
        attribute :>> elementId = "ITEM::ITM-MEA-022";
        attribute :>> sourceFile = "Rail_MBSE_Function_Interface_v1_final.xlsx";
        attribute :>> sourceSheet = "Item";
        attribute :>> sourceRow = 87;
    }
    item trace_74217e12422b76fc : TraceRecord {
        attribute :>> elementId = "PORTTYPE::PT-MEA-022";
        attribute :>> sourceFile = "Rail_MBSE_Function_Interface_v1_final.xlsx";
        attribute :>> sourceSheet = "Item";
        attribute :>> sourceRow = 87;
    }
    item trace_2ad563c914b1f717 : TraceRecord {
        attribute :>> elementId = "INTERFACETYPE::IF-MEA-022";
        attribute :>> sourceFile = "Rail_MBSE_Function_Interface_v1_final.xlsx";
        attribute :>> sourceSheet = "Item";
        attribute :>> sourceRow = 87;
    }
    item trace_953b319b3e4601b6 : TraceRecord {
        attribute :>> elementId = "ITEM::ITM-MEA-023";
        attribute :>> sourceFile = "Rail_MBSE_Function_Interface_v1_final.xlsx";
        attribute :>> sourceSheet = "Item";
        attribute :>> sourceRow = 88;
    }
    item trace_6c3c15b768f46dab : TraceRecord {
        attribute :>> elementId = "PORTTYPE::PT-MEA-023";
        attribute :>> sourceFile = "Rail_MBSE_Function_Interface_v1_final.xlsx";
        attribute :>> sourceSheet = "Item";
        attribute :>> sourceRow = 88;
    }
    item trace_fa83c5be55c0a71d : TraceRecord {
        attribute :>> elementId = "INTERFACETYPE::IF-MEA-023";
        attribute :>> sourceFile = "Rail_MBSE_Function_Interface_v1_final.xlsx";
        attribute :>> sourceSheet = "Item";
        attribute :>> sourceRow = 88;
    }
    item trace_6aa6b2086b882e34 : TraceRecord {
        attribute :>> elementId = "ITEM::ITM-MEA-024";
        attribute :>> sourceFile = "Rail_MBSE_Function_Interface_v1_final.xlsx";
        attribute :>> sourceSheet = "Item";
        attribute :>> sourceRow = 89;
    }
    item trace_162e943316324d02 : TraceRecord {
        attribute :>> elementId = "PORTTYPE::PT-MEA-024";
        attribute :>> sourceFile = "Rail_MBSE_Function_Interface_v1_final.xlsx";
        attribute :>> sourceSheet = "Item";
        attribute :>> sourceRow = 89;
    }
    item trace_eb61e3754353fbb1 : TraceRecord {
        attribute :>> elementId = "INTERFACETYPE::IF-MEA-024";
        attribute :>> sourceFile = "Rail_MBSE_Function_Interface_v1_final.xlsx";
        attribute :>> sourceSheet = "Item";
        attribute :>> sourceRow = 89;
    }
    item trace_69f35e4629a6f39a : TraceRecord {
        attribute :>> elementId = "ITEM::ITM-MEA-025";
        attribute :>> sourceFile = "Rail_MBSE_Function_Interface_v1_final.xlsx";
        attribute :>> sourceSheet = "Item";
        attribute :>> sourceRow = 90;
    }
    item trace_748cf725fdb18abb : TraceRecord {
        attribute :>> elementId = "PORTTYPE::PT-MEA-025";
        attribute :>> sourceFile = "Rail_MBSE_Function_Interface_v1_final.xlsx";
        attribute :>> sourceSheet = "Item";
        attribute :>> sourceRow = 90;
    }
    item trace_014d9af15f17c971 : TraceRecord {
        attribute :>> elementId = "INTERFACETYPE::IF-MEA-025";
        attribute :>> sourceFile = "Rail_MBSE_Function_Interface_v1_final.xlsx";
        attribute :>> sourceSheet = "Item";
        attribute :>> sourceRow = 90;
    }
    item trace_4d47a8fbb2ee49a4 : TraceRecord {
        attribute :>> elementId = "ITEM::ITM-MEA-026";
        attribute :>> sourceFile = "Rail_MBSE_Function_Interface_v1_final.xlsx";
        attribute :>> sourceSheet = "Item";
        attribute :>> sourceRow = 91;
    }
    item trace_d1923d493a1bdc50 : TraceRecord {
        attribute :>> elementId = "PORTTYPE::PT-MEA-026";
        attribute :>> sourceFile = "Rail_MBSE_Function_Interface_v1_final.xlsx";
        attribute :>> sourceSheet = "Item";
        attribute :>> sourceRow = 91;
    }
    item trace_090ab18af141c585 : TraceRecord {
        attribute :>> elementId = "INTERFACETYPE::IF-MEA-026";
        attribute :>> sourceFile = "Rail_MBSE_Function_Interface_v1_final.xlsx";
        attribute :>> sourceSheet = "Item";
        attribute :>> sourceRow = 91;
    }
    item trace_e790580cb5cc48d7 : TraceRecord {
        attribute :>> elementId = "ITEM::ITM-MEA-027";
        attribute :>> sourceFile = "Rail_MBSE_Function_Interface_v1_final.xlsx";
        attribute :>> sourceSheet = "Item";
        attribute :>> sourceRow = 92;
    }
    item trace_c58403b05a7c8c33 : TraceRecord {
        attribute :>> elementId = "PORTTYPE::PT-MEA-027";
        attribute :>> sourceFile = "Rail_MBSE_Function_Interface_v1_final.xlsx";
        attribute :>> sourceSheet = "Item";
        attribute :>> sourceRow = 92;
    }
    item trace_1224663059a3d339 : TraceRecord {
        attribute :>> elementId = "INTERFACETYPE::IF-MEA-027";
        attribute :>> sourceFile = "Rail_MBSE_Function_Interface_v1_final.xlsx";
        attribute :>> sourceSheet = "Item";
        attribute :>> sourceRow = 92;
    }
    item trace_539c908d4a99436e : TraceRecord {
        attribute :>> elementId = "ITEM::ITM-MEA-028";
        attribute :>> sourceFile = "Rail_MBSE_Function_Interface_v1_final.xlsx";
        attribute :>> sourceSheet = "Item";
        attribute :>> sourceRow = 93;
    }
    item trace_d9c78868b919e505 : TraceRecord {
        attribute :>> elementId = "PORTTYPE::PT-MEA-028";
        attribute :>> sourceFile = "Rail_MBSE_Function_Interface_v1_final.xlsx";
        attribute :>> sourceSheet = "Item";
        attribute :>> sourceRow = 93;
    }
    item trace_defc7908177cbca9 : TraceRecord {
        attribute :>> elementId = "INTERFACETYPE::IF-MEA-028";
        attribute :>> sourceFile = "Rail_MBSE_Function_Interface_v1_final.xlsx";
        attribute :>> sourceSheet = "Item";
        attribute :>> sourceRow = 93;
    }
    item trace_c5077e70c0b303a0 : TraceRecord {
        attribute :>> elementId = "ITEM::ITM-MEA-029";
        attribute :>> sourceFile = "Rail_MBSE_Function_Interface_v1_final.xlsx";
        attribute :>> sourceSheet = "Item";
        attribute :>> sourceRow = 94;
    }
    item trace_334aae35afa52f9c : TraceRecord {
        attribute :>> elementId = "PORTTYPE::PT-MEA-029";
        attribute :>> sourceFile = "Rail_MBSE_Function_Interface_v1_final.xlsx";
        attribute :>> sourceSheet = "Item";
        attribute :>> sourceRow = 94;
    }
    item trace_074e5acf377adca6 : TraceRecord {
        attribute :>> elementId = "INTERFACETYPE::IF-MEA-029";
        attribute :>> sourceFile = "Rail_MBSE_Function_Interface_v1_final.xlsx";
        attribute :>> sourceSheet = "Item";
        attribute :>> sourceRow = 94;
    }
    item trace_3202eac2fd51ec32 : TraceRecord {
        attribute :>> elementId = "ITEM::ITM-MEA-030";
        attribute :>> sourceFile = "Rail_MBSE_Function_Interface_v1_final.xlsx";
        attribute :>> sourceSheet = "Item";
        attribute :>> sourceRow = 95;
    }
    item trace_adbe542626583bb0 : TraceRecord {
        attribute :>> elementId = "PORTTYPE::PT-MEA-030";
        attribute :>> sourceFile = "Rail_MBSE_Function_Interface_v1_final.xlsx";
        attribute :>> sourceSheet = "Item";
        attribute :>> sourceRow = 95;
    }
    item trace_7478b55085fe36e3 : TraceRecord {
        attribute :>> elementId = "INTERFACETYPE::IF-MEA-030";
        attribute :>> sourceFile = "Rail_MBSE_Function_Interface_v1_final.xlsx";
        attribute :>> sourceSheet = "Item";
        attribute :>> sourceRow = 95;
    }
    item trace_89e02d7f5170ca77 : TraceRecord {
        attribute :>> elementId = "ITEM::ITM-MEA-031";
        attribute :>> sourceFile = "Rail_MBSE_Function_Interface_v1_final.xlsx";
        attribute :>> sourceSheet = "Item";
        attribute :>> sourceRow = 96;
    }
    item trace_15118247d3393dd4 : TraceRecord {
        attribute :>> elementId = "PORTTYPE::PT-MEA-031";
        attribute :>> sourceFile = "Rail_MBSE_Function_Interface_v1_final.xlsx";
        attribute :>> sourceSheet = "Item";
        attribute :>> sourceRow = 96;
    }
    item trace_1650709830698297 : TraceRecord {
        attribute :>> elementId = "INTERFACETYPE::IF-MEA-031";
        attribute :>> sourceFile = "Rail_MBSE_Function_Interface_v1_final.xlsx";
        attribute :>> sourceSheet = "Item";
        attribute :>> sourceRow = 96;
    }
    item trace_24ccb31e3f11413c : TraceRecord {
        attribute :>> elementId = "ITEM::ITM-PHY-001";
        attribute :>> sourceFile = "Rail_MBSE_Function_Interface_v1_final.xlsx";
        attribute :>> sourceSheet = "Item";
        attribute :>> sourceRow = 97;
    }
    item trace_ac887347c1952759 : TraceRecord {
        attribute :>> elementId = "PORTTYPE::PT-PHY-001";
        attribute :>> sourceFile = "Rail_MBSE_Function_Interface_v1_final.xlsx";
        attribute :>> sourceSheet = "Item";
        attribute :>> sourceRow = 97;
    }
    item trace_3cf3750806a5669c : TraceRecord {
        attribute :>> elementId = "INTERFACETYPE::IF-PHY-001";
        attribute :>> sourceFile = "Rail_MBSE_Function_Interface_v1_final.xlsx";
        attribute :>> sourceSheet = "Item";
        attribute :>> sourceRow = 97;
    }
    item trace_5a9274095f2567dd : TraceRecord {
        attribute :>> elementId = "ITEM::ITM-PHY-002";
        attribute :>> sourceFile = "Rail_MBSE_Function_Interface_v1_final.xlsx";
        attribute :>> sourceSheet = "Item";
        attribute :>> sourceRow = 98;
    }
    item trace_ea02042b5b17f000 : TraceRecord {
        attribute :>> elementId = "PORTTYPE::PT-PHY-002";
        attribute :>> sourceFile = "Rail_MBSE_Function_Interface_v1_final.xlsx";
        attribute :>> sourceSheet = "Item";
        attribute :>> sourceRow = 98;
    }
    item trace_e8d227888d93d3d8 : TraceRecord {
        attribute :>> elementId = "INTERFACETYPE::IF-PHY-002";
        attribute :>> sourceFile = "Rail_MBSE_Function_Interface_v1_final.xlsx";
        attribute :>> sourceSheet = "Item";
        attribute :>> sourceRow = 98;
    }
    item trace_b006913f264ef9a6 : TraceRecord {
        attribute :>> elementId = "ITEM::ITM-PHY-003";
        attribute :>> sourceFile = "Rail_MBSE_Function_Interface_v1_final.xlsx";
        attribute :>> sourceSheet = "Item";
        attribute :>> sourceRow = 99;
    }
    item trace_6e8ba51243544d91 : TraceRecord {
        attribute :>> elementId = "PORTTYPE::PT-PHY-003";
        attribute :>> sourceFile = "Rail_MBSE_Function_Interface_v1_final.xlsx";
        attribute :>> sourceSheet = "Item";
        attribute :>> sourceRow = 99;
    }
    item trace_0db62a8eb47597b0 : TraceRecord {
        attribute :>> elementId = "INTERFACETYPE::IF-PHY-003";
        attribute :>> sourceFile = "Rail_MBSE_Function_Interface_v1_final.xlsx";
        attribute :>> sourceSheet = "Item";
        attribute :>> sourceRow = 99;
    }
    item trace_c5636070d91896ba : TraceRecord {
        attribute :>> elementId = "ITEM::ITM-PHY-004";
        attribute :>> sourceFile = "Rail_MBSE_Function_Interface_v1_final.xlsx";
        attribute :>> sourceSheet = "Item";
        attribute :>> sourceRow = 100;
    }
    item trace_f5c1d5712229ece9 : TraceRecord {
        attribute :>> elementId = "PORTTYPE::PT-PHY-004";
        attribute :>> sourceFile = "Rail_MBSE_Function_Interface_v1_final.xlsx";
        attribute :>> sourceSheet = "Item";
        attribute :>> sourceRow = 100;
    }
    item trace_7237ca6ebf919090 : TraceRecord {
        attribute :>> elementId = "INTERFACETYPE::IF-PHY-004";
        attribute :>> sourceFile = "Rail_MBSE_Function_Interface_v1_final.xlsx";
        attribute :>> sourceSheet = "Item";
        attribute :>> sourceRow = 100;
    }
    item trace_bb2c226458b60709 : TraceRecord {
        attribute :>> elementId = "ITEM::ITM-PHY-005";
        attribute :>> sourceFile = "Rail_MBSE_Function_Interface_v1_final.xlsx";
        attribute :>> sourceSheet = "Item";
        attribute :>> sourceRow = 101;
    }
    item trace_e5848191304dd9a5 : TraceRecord {
        attribute :>> elementId = "PORTTYPE::PT-PHY-005";
        attribute :>> sourceFile = "Rail_MBSE_Function_Interface_v1_final.xlsx";
        attribute :>> sourceSheet = "Item";
        attribute :>> sourceRow = 101;
    }
    item trace_ee7245d8c7885752 : TraceRecord {
        attribute :>> elementId = "INTERFACETYPE::IF-PHY-005";
        attribute :>> sourceFile = "Rail_MBSE_Function_Interface_v1_final.xlsx";
        attribute :>> sourceSheet = "Item";
        attribute :>> sourceRow = 101;
    }
    item trace_83c3c9ec05388393 : TraceRecord {
        attribute :>> elementId = "ITEM::ITM-PHY-006";
        attribute :>> sourceFile = "Rail_MBSE_Function_Interface_v1_final.xlsx";
        attribute :>> sourceSheet = "Item";
        attribute :>> sourceRow = 102;
    }
    item trace_7d67ac831e516a07 : TraceRecord {
        attribute :>> elementId = "PORTTYPE::PT-PHY-006";
        attribute :>> sourceFile = "Rail_MBSE_Function_Interface_v1_final.xlsx";
        attribute :>> sourceSheet = "Item";
        attribute :>> sourceRow = 102;
    }
    item trace_aa0b05034a9e05c9 : TraceRecord {
        attribute :>> elementId = "INTERFACETYPE::IF-PHY-006";
        attribute :>> sourceFile = "Rail_MBSE_Function_Interface_v1_final.xlsx";
        attribute :>> sourceSheet = "Item";
        attribute :>> sourceRow = 102;
    }
    item trace_43810957d5ccfc96 : TraceRecord {
        attribute :>> elementId = "ITEM::ITM-PHY-007";
        attribute :>> sourceFile = "Rail_MBSE_Function_Interface_v1_final.xlsx";
        attribute :>> sourceSheet = "Item";
        attribute :>> sourceRow = 103;
    }
    item trace_98bb4dfd71e9ceb3 : TraceRecord {
        attribute :>> elementId = "PORTTYPE::PT-PHY-007";
        attribute :>> sourceFile = "Rail_MBSE_Function_Interface_v1_final.xlsx";
        attribute :>> sourceSheet = "Item";
        attribute :>> sourceRow = 103;
    }
    item trace_d58b715540bc3452 : TraceRecord {
        attribute :>> elementId = "INTERFACETYPE::IF-PHY-007";
        attribute :>> sourceFile = "Rail_MBSE_Function_Interface_v1_final.xlsx";
        attribute :>> sourceSheet = "Item";
        attribute :>> sourceRow = 103;
    }
    item trace_fde65cc6addabe04 : TraceRecord {
        attribute :>> elementId = "ITEM::ITM-PHY-008";
        attribute :>> sourceFile = "Rail_MBSE_Function_Interface_v1_final.xlsx";
        attribute :>> sourceSheet = "Item";
        attribute :>> sourceRow = 104;
    }
    item trace_57bbdd353ba1a423 : TraceRecord {
        attribute :>> elementId = "PORTTYPE::PT-PHY-008";
        attribute :>> sourceFile = "Rail_MBSE_Function_Interface_v1_final.xlsx";
        attribute :>> sourceSheet = "Item";
        attribute :>> sourceRow = 104;
    }
    item trace_2abab1509c771a60 : TraceRecord {
        attribute :>> elementId = "INTERFACETYPE::IF-PHY-008";
        attribute :>> sourceFile = "Rail_MBSE_Function_Interface_v1_final.xlsx";
        attribute :>> sourceSheet = "Item";
        attribute :>> sourceRow = 104;
    }
    item trace_f78dff4c2bb6a359 : TraceRecord {
        attribute :>> elementId = "ITEM::ITM-PHY-009";
        attribute :>> sourceFile = "Rail_MBSE_Function_Interface_v1_final.xlsx";
        attribute :>> sourceSheet = "Item";
        attribute :>> sourceRow = 105;
    }
    item trace_433e9f1c6b3a9cdc : TraceRecord {
        attribute :>> elementId = "PORTTYPE::PT-PHY-009";
        attribute :>> sourceFile = "Rail_MBSE_Function_Interface_v1_final.xlsx";
        attribute :>> sourceSheet = "Item";
        attribute :>> sourceRow = 105;
    }
    item trace_9560449c2d3d60b9 : TraceRecord {
        attribute :>> elementId = "INTERFACETYPE::IF-PHY-009";
        attribute :>> sourceFile = "Rail_MBSE_Function_Interface_v1_final.xlsx";
        attribute :>> sourceSheet = "Item";
        attribute :>> sourceRow = 105;
    }
    item trace_8393c5effe57c122 : TraceRecord {
        attribute :>> elementId = "ITEM::ITM-PHY-010";
        attribute :>> sourceFile = "Rail_MBSE_Function_Interface_v1_final.xlsx";
        attribute :>> sourceSheet = "Item";
        attribute :>> sourceRow = 106;
    }
    item trace_714b0646c8b6f547 : TraceRecord {
        attribute :>> elementId = "PORTTYPE::PT-PHY-010";
        attribute :>> sourceFile = "Rail_MBSE_Function_Interface_v1_final.xlsx";
        attribute :>> sourceSheet = "Item";
        attribute :>> sourceRow = 106;
    }
    item trace_73181e0df53fd484 : TraceRecord {
        attribute :>> elementId = "INTERFACETYPE::IF-PHY-010";
        attribute :>> sourceFile = "Rail_MBSE_Function_Interface_v1_final.xlsx";
        attribute :>> sourceSheet = "Item";
        attribute :>> sourceRow = 106;
    }
    item trace_72aea3136a0471c5 : TraceRecord {
        attribute :>> elementId = "ITEM::ITM-PHY-011";
        attribute :>> sourceFile = "Rail_MBSE_Function_Interface_v1_final.xlsx";
        attribute :>> sourceSheet = "Item";
        attribute :>> sourceRow = 107;
    }
    item trace_d458f740ff38ab15 : TraceRecord {
        attribute :>> elementId = "PORTTYPE::PT-PHY-011";
        attribute :>> sourceFile = "Rail_MBSE_Function_Interface_v1_final.xlsx";
        attribute :>> sourceSheet = "Item";
        attribute :>> sourceRow = 107;
    }
    item trace_add461b01db567ed : TraceRecord {
        attribute :>> elementId = "INTERFACETYPE::IF-PHY-011";
        attribute :>> sourceFile = "Rail_MBSE_Function_Interface_v1_final.xlsx";
        attribute :>> sourceSheet = "Item";
        attribute :>> sourceRow = 107;
    }
    item trace_5fed99cf96afefca : TraceRecord {
        attribute :>> elementId = "ITEM::ITM-PHY-012";
        attribute :>> sourceFile = "Rail_MBSE_Function_Interface_v1_final.xlsx";
        attribute :>> sourceSheet = "Item";
        attribute :>> sourceRow = 108;
    }
    item trace_b5e989d8c47e1a76 : TraceRecord {
        attribute :>> elementId = "PORTTYPE::PT-PHY-012";
        attribute :>> sourceFile = "Rail_MBSE_Function_Interface_v1_final.xlsx";
        attribute :>> sourceSheet = "Item";
        attribute :>> sourceRow = 108;
    }
    item trace_3cf578964facfe81 : TraceRecord {
        attribute :>> elementId = "INTERFACETYPE::IF-PHY-012";
        attribute :>> sourceFile = "Rail_MBSE_Function_Interface_v1_final.xlsx";
        attribute :>> sourceSheet = "Item";
        attribute :>> sourceRow = 108;
    }
    item trace_6d8f79ac52b7ea16 : TraceRecord {
        attribute :>> elementId = "ITEM::ITM-PHY-013";
        attribute :>> sourceFile = "Rail_MBSE_Function_Interface_v1_final.xlsx";
        attribute :>> sourceSheet = "Item";
        attribute :>> sourceRow = 109;
    }
    item trace_e9e8e89e314782c1 : TraceRecord {
        attribute :>> elementId = "PORTTYPE::PT-PHY-013";
        attribute :>> sourceFile = "Rail_MBSE_Function_Interface_v1_final.xlsx";
        attribute :>> sourceSheet = "Item";
        attribute :>> sourceRow = 109;
    }
    item trace_ff38e9422dc05470 : TraceRecord {
        attribute :>> elementId = "INTERFACETYPE::IF-PHY-013";
        attribute :>> sourceFile = "Rail_MBSE_Function_Interface_v1_final.xlsx";
        attribute :>> sourceSheet = "Item";
        attribute :>> sourceRow = 109;
    }
    item trace_dcd36a3cd9b1254d : TraceRecord {
        attribute :>> elementId = "ITEM::ITM-PHY-014";
        attribute :>> sourceFile = "Rail_MBSE_Function_Interface_v1_final.xlsx";
        attribute :>> sourceSheet = "Item";
        attribute :>> sourceRow = 110;
    }
    item trace_5a85149968a2fb7e : TraceRecord {
        attribute :>> elementId = "PORTTYPE::PT-PHY-014";
        attribute :>> sourceFile = "Rail_MBSE_Function_Interface_v1_final.xlsx";
        attribute :>> sourceSheet = "Item";
        attribute :>> sourceRow = 110;
    }
    item trace_75e9f3db1e3d6410 : TraceRecord {
        attribute :>> elementId = "INTERFACETYPE::IF-PHY-014";
        attribute :>> sourceFile = "Rail_MBSE_Function_Interface_v1_final.xlsx";
        attribute :>> sourceSheet = "Item";
        attribute :>> sourceRow = 110;
    }
    item trace_9003be46dd8aee7d : TraceRecord {
        attribute :>> elementId = "ITEM::ITM-PHY-015";
        attribute :>> sourceFile = "Rail_MBSE_Function_Interface_v1_final.xlsx";
        attribute :>> sourceSheet = "Item";
        attribute :>> sourceRow = 111;
    }
    item trace_c6f78d92cd525d27 : TraceRecord {
        attribute :>> elementId = "PORTTYPE::PT-PHY-015";
        attribute :>> sourceFile = "Rail_MBSE_Function_Interface_v1_final.xlsx";
        attribute :>> sourceSheet = "Item";
        attribute :>> sourceRow = 111;
    }
    item trace_1e57c053def99068 : TraceRecord {
        attribute :>> elementId = "INTERFACETYPE::IF-PHY-015";
        attribute :>> sourceFile = "Rail_MBSE_Function_Interface_v1_final.xlsx";
        attribute :>> sourceSheet = "Item";
        attribute :>> sourceRow = 111;
    }
    item trace_f7a3bb0bd4a3651e : TraceRecord {
        attribute :>> elementId = "ITEM::ITM-PHY-016";
        attribute :>> sourceFile = "Rail_MBSE_Function_Interface_v1_final.xlsx";
        attribute :>> sourceSheet = "Item";
        attribute :>> sourceRow = 112;
    }
    item trace_eba49b62f0cfdf52 : TraceRecord {
        attribute :>> elementId = "PORTTYPE::PT-PHY-016";
        attribute :>> sourceFile = "Rail_MBSE_Function_Interface_v1_final.xlsx";
        attribute :>> sourceSheet = "Item";
        attribute :>> sourceRow = 112;
    }
    item trace_ac0699e42d95d34c : TraceRecord {
        attribute :>> elementId = "INTERFACETYPE::IF-PHY-016";
        attribute :>> sourceFile = "Rail_MBSE_Function_Interface_v1_final.xlsx";
        attribute :>> sourceSheet = "Item";
        attribute :>> sourceRow = 112;
    }
    item trace_8ee2168481b3efaa : TraceRecord {
        attribute :>> elementId = "ITEM::ITM-STA-001";
        attribute :>> sourceFile = "Rail_MBSE_Function_Interface_v1_final.xlsx";
        attribute :>> sourceSheet = "Item";
        attribute :>> sourceRow = 113;
    }
    item trace_aa025bd69873bd14 : TraceRecord {
        attribute :>> elementId = "PORTTYPE::PT-STA-001";
        attribute :>> sourceFile = "Rail_MBSE_Function_Interface_v1_final.xlsx";
        attribute :>> sourceSheet = "Item";
        attribute :>> sourceRow = 113;
    }
    item trace_2ef540a795e51857 : TraceRecord {
        attribute :>> elementId = "INTERFACETYPE::IF-STA-001";
        attribute :>> sourceFile = "Rail_MBSE_Function_Interface_v1_final.xlsx";
        attribute :>> sourceSheet = "Item";
        attribute :>> sourceRow = 113;
    }
    item trace_0a318e8baee38bbb : TraceRecord {
        attribute :>> elementId = "ITEM::ITM-STA-002";
        attribute :>> sourceFile = "Rail_MBSE_Function_Interface_v1_final.xlsx";
        attribute :>> sourceSheet = "Item";
        attribute :>> sourceRow = 114;
    }
    item trace_ee5b9244997fbec1 : TraceRecord {
        attribute :>> elementId = "PORTTYPE::PT-STA-002";
        attribute :>> sourceFile = "Rail_MBSE_Function_Interface_v1_final.xlsx";
        attribute :>> sourceSheet = "Item";
        attribute :>> sourceRow = 114;
    }
    item trace_6a80bea52398c8ba : TraceRecord {
        attribute :>> elementId = "INTERFACETYPE::IF-STA-002";
        attribute :>> sourceFile = "Rail_MBSE_Function_Interface_v1_final.xlsx";
        attribute :>> sourceSheet = "Item";
        attribute :>> sourceRow = 114;
    }
    item trace_235dbd145e981ed0 : TraceRecord {
        attribute :>> elementId = "ITEM::ITM-STA-003";
        attribute :>> sourceFile = "Rail_MBSE_Function_Interface_v1_final.xlsx";
        attribute :>> sourceSheet = "Item";
        attribute :>> sourceRow = 115;
    }
    item trace_2b4afda5d9186041 : TraceRecord {
        attribute :>> elementId = "PORTTYPE::PT-STA-003";
        attribute :>> sourceFile = "Rail_MBSE_Function_Interface_v1_final.xlsx";
        attribute :>> sourceSheet = "Item";
        attribute :>> sourceRow = 115;
    }
    item trace_163c8ee9f7e3ea1c : TraceRecord {
        attribute :>> elementId = "INTERFACETYPE::IF-STA-003";
        attribute :>> sourceFile = "Rail_MBSE_Function_Interface_v1_final.xlsx";
        attribute :>> sourceSheet = "Item";
        attribute :>> sourceRow = 115;
    }
    item trace_22dbbec1bf0a2158 : TraceRecord {
        attribute :>> elementId = "ITEM::ITM-STA-004";
        attribute :>> sourceFile = "Rail_MBSE_Function_Interface_v1_final.xlsx";
        attribute :>> sourceSheet = "Item";
        attribute :>> sourceRow = 116;
    }
    item trace_f374896ec899cecf : TraceRecord {
        attribute :>> elementId = "PORTTYPE::PT-STA-004";
        attribute :>> sourceFile = "Rail_MBSE_Function_Interface_v1_final.xlsx";
        attribute :>> sourceSheet = "Item";
        attribute :>> sourceRow = 116;
    }
    item trace_7f09857fc58e818a : TraceRecord {
        attribute :>> elementId = "INTERFACETYPE::IF-STA-004";
        attribute :>> sourceFile = "Rail_MBSE_Function_Interface_v1_final.xlsx";
        attribute :>> sourceSheet = "Item";
        attribute :>> sourceRow = 116;
    }
    item trace_eaa0b2c7edf555c8 : TraceRecord {
        attribute :>> elementId = "ITEM::ITM-STA-005";
        attribute :>> sourceFile = "Rail_MBSE_Function_Interface_v1_final.xlsx";
        attribute :>> sourceSheet = "Item";
        attribute :>> sourceRow = 117;
    }
    item trace_f06e8d877ccc61d6 : TraceRecord {
        attribute :>> elementId = "PORTTYPE::PT-STA-005";
        attribute :>> sourceFile = "Rail_MBSE_Function_Interface_v1_final.xlsx";
        attribute :>> sourceSheet = "Item";
        attribute :>> sourceRow = 117;
    }
    item trace_bdaedcbd8d89f561 : TraceRecord {
        attribute :>> elementId = "INTERFACETYPE::IF-STA-005";
        attribute :>> sourceFile = "Rail_MBSE_Function_Interface_v1_final.xlsx";
        attribute :>> sourceSheet = "Item";
        attribute :>> sourceRow = 117;
    }
    item trace_e32856483de29337 : TraceRecord {
        attribute :>> elementId = "ITEM::ITM-STA-006";
        attribute :>> sourceFile = "Rail_MBSE_Function_Interface_v1_final.xlsx";
        attribute :>> sourceSheet = "Item";
        attribute :>> sourceRow = 118;
    }
    item trace_335abfdea741da66 : TraceRecord {
        attribute :>> elementId = "PORTTYPE::PT-STA-006";
        attribute :>> sourceFile = "Rail_MBSE_Function_Interface_v1_final.xlsx";
        attribute :>> sourceSheet = "Item";
        attribute :>> sourceRow = 118;
    }
    item trace_8a532093d9380136 : TraceRecord {
        attribute :>> elementId = "INTERFACETYPE::IF-STA-006";
        attribute :>> sourceFile = "Rail_MBSE_Function_Interface_v1_final.xlsx";
        attribute :>> sourceSheet = "Item";
        attribute :>> sourceRow = 118;
    }
    item trace_57e8526521131ffc : TraceRecord {
        attribute :>> elementId = "ITEM::ITM-STA-007";
        attribute :>> sourceFile = "Rail_MBSE_Function_Interface_v1_final.xlsx";
        attribute :>> sourceSheet = "Item";
        attribute :>> sourceRow = 119;
    }
    item trace_e61673b6b3a14d03 : TraceRecord {
        attribute :>> elementId = "PORTTYPE::PT-STA-007";
        attribute :>> sourceFile = "Rail_MBSE_Function_Interface_v1_final.xlsx";
        attribute :>> sourceSheet = "Item";
        attribute :>> sourceRow = 119;
    }
    item trace_400d7d3c948d394b : TraceRecord {
        attribute :>> elementId = "INTERFACETYPE::IF-STA-007";
        attribute :>> sourceFile = "Rail_MBSE_Function_Interface_v1_final.xlsx";
        attribute :>> sourceSheet = "Item";
        attribute :>> sourceRow = 119;
    }
    item trace_aef9e0fe86321904 : TraceRecord {
        attribute :>> elementId = "ITEM::ITM-STA-008";
        attribute :>> sourceFile = "Rail_MBSE_Function_Interface_v1_final.xlsx";
        attribute :>> sourceSheet = "Item";
        attribute :>> sourceRow = 120;
    }
    item trace_e9def2964743c681 : TraceRecord {
        attribute :>> elementId = "PORTTYPE::PT-STA-008";
        attribute :>> sourceFile = "Rail_MBSE_Function_Interface_v1_final.xlsx";
        attribute :>> sourceSheet = "Item";
        attribute :>> sourceRow = 120;
    }
    item trace_193034e739fac9e9 : TraceRecord {
        attribute :>> elementId = "INTERFACETYPE::IF-STA-008";
        attribute :>> sourceFile = "Rail_MBSE_Function_Interface_v1_final.xlsx";
        attribute :>> sourceSheet = "Item";
        attribute :>> sourceRow = 120;
    }
    item trace_c818e78b0b81746a : TraceRecord {
        attribute :>> elementId = "ITEM::ITM-STA-009";
        attribute :>> sourceFile = "Rail_MBSE_Function_Interface_v1_final.xlsx";
        attribute :>> sourceSheet = "Item";
        attribute :>> sourceRow = 121;
    }
    item trace_3d44c1a616cb998d : TraceRecord {
        attribute :>> elementId = "PORTTYPE::PT-STA-009";
        attribute :>> sourceFile = "Rail_MBSE_Function_Interface_v1_final.xlsx";
        attribute :>> sourceSheet = "Item";
        attribute :>> sourceRow = 121;
    }
    item trace_d5ec5a99f2e9f3d3 : TraceRecord {
        attribute :>> elementId = "INTERFACETYPE::IF-STA-009";
        attribute :>> sourceFile = "Rail_MBSE_Function_Interface_v1_final.xlsx";
        attribute :>> sourceSheet = "Item";
        attribute :>> sourceRow = 121;
    }
    item trace_62387954bf1b56b8 : TraceRecord {
        attribute :>> elementId = "ITEM::ITM-STA-010";
        attribute :>> sourceFile = "Rail_MBSE_Function_Interface_v1_final.xlsx";
        attribute :>> sourceSheet = "Item";
        attribute :>> sourceRow = 122;
    }
    item trace_86bf6eb3778dc879 : TraceRecord {
        attribute :>> elementId = "PORTTYPE::PT-STA-010";
        attribute :>> sourceFile = "Rail_MBSE_Function_Interface_v1_final.xlsx";
        attribute :>> sourceSheet = "Item";
        attribute :>> sourceRow = 122;
    }
    item trace_b521a5a5d9d529f8 : TraceRecord {
        attribute :>> elementId = "INTERFACETYPE::IF-STA-010";
        attribute :>> sourceFile = "Rail_MBSE_Function_Interface_v1_final.xlsx";
        attribute :>> sourceSheet = "Item";
        attribute :>> sourceRow = 122;
    }
    item trace_11afab9aa94553e3 : TraceRecord {
        attribute :>> elementId = "ITEM::ITM-STA-011";
        attribute :>> sourceFile = "Rail_MBSE_Function_Interface_v1_final.xlsx";
        attribute :>> sourceSheet = "Item";
        attribute :>> sourceRow = 123;
    }
    item trace_b03ccbab6a1c9701 : TraceRecord {
        attribute :>> elementId = "PORTTYPE::PT-STA-011";
        attribute :>> sourceFile = "Rail_MBSE_Function_Interface_v1_final.xlsx";
        attribute :>> sourceSheet = "Item";
        attribute :>> sourceRow = 123;
    }
    item trace_a4f9d8069bd5c6d0 : TraceRecord {
        attribute :>> elementId = "INTERFACETYPE::IF-STA-011";
        attribute :>> sourceFile = "Rail_MBSE_Function_Interface_v1_final.xlsx";
        attribute :>> sourceSheet = "Item";
        attribute :>> sourceRow = 123;
    }
    item trace_7107d18b7f0ddc39 : TraceRecord {
        attribute :>> elementId = "ITEM::ITM-STA-012";
        attribute :>> sourceFile = "Rail_MBSE_Function_Interface_v1_final.xlsx";
        attribute :>> sourceSheet = "Item";
        attribute :>> sourceRow = 124;
    }
    item trace_6463b71f6707f1d0 : TraceRecord {
        attribute :>> elementId = "PORTTYPE::PT-STA-012";
        attribute :>> sourceFile = "Rail_MBSE_Function_Interface_v1_final.xlsx";
        attribute :>> sourceSheet = "Item";
        attribute :>> sourceRow = 124;
    }
    item trace_0b639fc890bbfadd : TraceRecord {
        attribute :>> elementId = "INTERFACETYPE::IF-STA-012";
        attribute :>> sourceFile = "Rail_MBSE_Function_Interface_v1_final.xlsx";
        attribute :>> sourceSheet = "Item";
        attribute :>> sourceRow = 124;
    }
    item trace_237a32823bd75d16 : TraceRecord {
        attribute :>> elementId = "ITEM::ITM-STA-013";
        attribute :>> sourceFile = "Rail_MBSE_Function_Interface_v1_final.xlsx";
        attribute :>> sourceSheet = "Item";
        attribute :>> sourceRow = 125;
    }
    item trace_5c891a0dd94ced38 : TraceRecord {
        attribute :>> elementId = "PORTTYPE::PT-STA-013";
        attribute :>> sourceFile = "Rail_MBSE_Function_Interface_v1_final.xlsx";
        attribute :>> sourceSheet = "Item";
        attribute :>> sourceRow = 125;
    }
    item trace_6e31383a32104f92 : TraceRecord {
        attribute :>> elementId = "INTERFACETYPE::IF-STA-013";
        attribute :>> sourceFile = "Rail_MBSE_Function_Interface_v1_final.xlsx";
        attribute :>> sourceSheet = "Item";
        attribute :>> sourceRow = 125;
    }
    item trace_cdfabb1f8bcc8125 : TraceRecord {
        attribute :>> elementId = "ITEM::ITM-STA-014";
        attribute :>> sourceFile = "Rail_MBSE_Function_Interface_v1_final.xlsx";
        attribute :>> sourceSheet = "Item";
        attribute :>> sourceRow = 126;
    }
    item trace_cc9b3cd0003cedeb : TraceRecord {
        attribute :>> elementId = "PORTTYPE::PT-STA-014";
        attribute :>> sourceFile = "Rail_MBSE_Function_Interface_v1_final.xlsx";
        attribute :>> sourceSheet = "Item";
        attribute :>> sourceRow = 126;
    }
    item trace_81384803671846ba : TraceRecord {
        attribute :>> elementId = "INTERFACETYPE::IF-STA-014";
        attribute :>> sourceFile = "Rail_MBSE_Function_Interface_v1_final.xlsx";
        attribute :>> sourceSheet = "Item";
        attribute :>> sourceRow = 126;
    }
    item trace_f25b30027554f63a : TraceRecord {
        attribute :>> elementId = "ITEM::ITM-STA-015";
        attribute :>> sourceFile = "Rail_MBSE_Function_Interface_v1_final.xlsx";
        attribute :>> sourceSheet = "Item";
        attribute :>> sourceRow = 127;
    }
    item trace_c234967de2f50b89 : TraceRecord {
        attribute :>> elementId = "PORTTYPE::PT-STA-015";
        attribute :>> sourceFile = "Rail_MBSE_Function_Interface_v1_final.xlsx";
        attribute :>> sourceSheet = "Item";
        attribute :>> sourceRow = 127;
    }
    item trace_8e81e4457f0dcd2a : TraceRecord {
        attribute :>> elementId = "INTERFACETYPE::IF-STA-015";
        attribute :>> sourceFile = "Rail_MBSE_Function_Interface_v1_final.xlsx";
        attribute :>> sourceSheet = "Item";
        attribute :>> sourceRow = 127;
    }
    item trace_bc1723254b607d57 : TraceRecord {
        attribute :>> elementId = "ITEM::ITM-STA-016";
        attribute :>> sourceFile = "Rail_MBSE_Function_Interface_v1_final.xlsx";
        attribute :>> sourceSheet = "Item";
        attribute :>> sourceRow = 128;
    }
    item trace_e25c790b6a06b238 : TraceRecord {
        attribute :>> elementId = "PORTTYPE::PT-STA-016";
        attribute :>> sourceFile = "Rail_MBSE_Function_Interface_v1_final.xlsx";
        attribute :>> sourceSheet = "Item";
        attribute :>> sourceRow = 128;
    }
    item trace_c2eb4c554ee5c2ae : TraceRecord {
        attribute :>> elementId = "INTERFACETYPE::IF-STA-016";
        attribute :>> sourceFile = "Rail_MBSE_Function_Interface_v1_final.xlsx";
        attribute :>> sourceSheet = "Item";
        attribute :>> sourceRow = 128;
    }
    item trace_c2805a315f66d51f : TraceRecord {
        attribute :>> elementId = "ITEM::ITM-STA-017";
        attribute :>> sourceFile = "Rail_MBSE_Function_Interface_v1_final.xlsx";
        attribute :>> sourceSheet = "Item";
        attribute :>> sourceRow = 129;
    }
    item trace_bb13b5b5513380ca : TraceRecord {
        attribute :>> elementId = "PORTTYPE::PT-STA-017";
        attribute :>> sourceFile = "Rail_MBSE_Function_Interface_v1_final.xlsx";
        attribute :>> sourceSheet = "Item";
        attribute :>> sourceRow = 129;
    }
    item trace_0c2b78b396179e10 : TraceRecord {
        attribute :>> elementId = "INTERFACETYPE::IF-STA-017";
        attribute :>> sourceFile = "Rail_MBSE_Function_Interface_v1_final.xlsx";
        attribute :>> sourceSheet = "Item";
        attribute :>> sourceRow = 129;
    }
    item trace_665a30cff6c44896 : TraceRecord {
        attribute :>> elementId = "ITEM::ITM-STA-018";
        attribute :>> sourceFile = "Rail_MBSE_Function_Interface_v1_final.xlsx";
        attribute :>> sourceSheet = "Item";
        attribute :>> sourceRow = 130;
    }
    item trace_c9fb9dba35cbd950 : TraceRecord {
        attribute :>> elementId = "PORTTYPE::PT-STA-018";
        attribute :>> sourceFile = "Rail_MBSE_Function_Interface_v1_final.xlsx";
        attribute :>> sourceSheet = "Item";
        attribute :>> sourceRow = 130;
    }
    item trace_a7445a78ba955f0e : TraceRecord {
        attribute :>> elementId = "INTERFACETYPE::IF-STA-018";
        attribute :>> sourceFile = "Rail_MBSE_Function_Interface_v1_final.xlsx";
        attribute :>> sourceSheet = "Item";
        attribute :>> sourceRow = 130;
    }
    item trace_036bb4f43f5f025f : TraceRecord {
        attribute :>> elementId = "ITEM::ITM-STA-019";
        attribute :>> sourceFile = "Rail_MBSE_Function_Interface_v1_final.xlsx";
        attribute :>> sourceSheet = "Item";
        attribute :>> sourceRow = 131;
    }
    item trace_9c40bbd5e3c59d91 : TraceRecord {
        attribute :>> elementId = "PORTTYPE::PT-STA-019";
        attribute :>> sourceFile = "Rail_MBSE_Function_Interface_v1_final.xlsx";
        attribute :>> sourceSheet = "Item";
        attribute :>> sourceRow = 131;
    }
    item trace_1ce232993a40c8db : TraceRecord {
        attribute :>> elementId = "INTERFACETYPE::IF-STA-019";
        attribute :>> sourceFile = "Rail_MBSE_Function_Interface_v1_final.xlsx";
        attribute :>> sourceSheet = "Item";
        attribute :>> sourceRow = 131;
    }
    item trace_5593b83d675c6c8c : TraceRecord {
        attribute :>> elementId = "ITEM::ITM-STA-020";
        attribute :>> sourceFile = "Rail_MBSE_Function_Interface_v1_final.xlsx";
        attribute :>> sourceSheet = "Item";
        attribute :>> sourceRow = 132;
    }
    item trace_dd4fd13f5537df52 : TraceRecord {
        attribute :>> elementId = "PORTTYPE::PT-STA-020";
        attribute :>> sourceFile = "Rail_MBSE_Function_Interface_v1_final.xlsx";
        attribute :>> sourceSheet = "Item";
        attribute :>> sourceRow = 132;
    }
    item trace_e2227f0eb9db8958 : TraceRecord {
        attribute :>> elementId = "INTERFACETYPE::IF-STA-020";
        attribute :>> sourceFile = "Rail_MBSE_Function_Interface_v1_final.xlsx";
        attribute :>> sourceSheet = "Item";
        attribute :>> sourceRow = 132;
    }
    item trace_d06d197383332dce : TraceRecord {
        attribute :>> elementId = "ITEM::ITM-STA-021";
        attribute :>> sourceFile = "Rail_MBSE_Function_Interface_v1_final.xlsx";
        attribute :>> sourceSheet = "Item";
        attribute :>> sourceRow = 133;
    }
    item trace_9be35a93e2a53418 : TraceRecord {
        attribute :>> elementId = "PORTTYPE::PT-STA-021";
        attribute :>> sourceFile = "Rail_MBSE_Function_Interface_v1_final.xlsx";
        attribute :>> sourceSheet = "Item";
        attribute :>> sourceRow = 133;
    }
    item trace_ffae056c55e4599e : TraceRecord {
        attribute :>> elementId = "INTERFACETYPE::IF-STA-021";
        attribute :>> sourceFile = "Rail_MBSE_Function_Interface_v1_final.xlsx";
        attribute :>> sourceSheet = "Item";
        attribute :>> sourceRow = 133;
    }
    item trace_008d684048bd5cd6 : TraceRecord {
        attribute :>> elementId = "ITEM::ITM-STA-022";
        attribute :>> sourceFile = "Rail_MBSE_Function_Interface_v1_final.xlsx";
        attribute :>> sourceSheet = "Item";
        attribute :>> sourceRow = 134;
    }
    item trace_079197d4661f407f : TraceRecord {
        attribute :>> elementId = "PORTTYPE::PT-STA-022";
        attribute :>> sourceFile = "Rail_MBSE_Function_Interface_v1_final.xlsx";
        attribute :>> sourceSheet = "Item";
        attribute :>> sourceRow = 134;
    }
    item trace_aa6d9cddc0d413bd : TraceRecord {
        attribute :>> elementId = "INTERFACETYPE::IF-STA-022";
        attribute :>> sourceFile = "Rail_MBSE_Function_Interface_v1_final.xlsx";
        attribute :>> sourceSheet = "Item";
        attribute :>> sourceRow = 134;
    }
    item trace_5a1414b5d1624e81 : TraceRecord {
        attribute :>> elementId = "ITEM::ITM-STA-023";
        attribute :>> sourceFile = "Rail_MBSE_Function_Interface_v1_final.xlsx";
        attribute :>> sourceSheet = "Item";
        attribute :>> sourceRow = 135;
    }
    item trace_7e48108cf48790e4 : TraceRecord {
        attribute :>> elementId = "PORTTYPE::PT-STA-023";
        attribute :>> sourceFile = "Rail_MBSE_Function_Interface_v1_final.xlsx";
        attribute :>> sourceSheet = "Item";
        attribute :>> sourceRow = 135;
    }
    item trace_4ad1febe54747c9e : TraceRecord {
        attribute :>> elementId = "INTERFACETYPE::IF-STA-023";
        attribute :>> sourceFile = "Rail_MBSE_Function_Interface_v1_final.xlsx";
        attribute :>> sourceSheet = "Item";
        attribute :>> sourceRow = 135;
    }
    item trace_4ee2ad1d7bce29d4 : TraceRecord {
        attribute :>> elementId = "ITEM::ITM-STA-024";
        attribute :>> sourceFile = "Rail_MBSE_Function_Interface_v1_final.xlsx";
        attribute :>> sourceSheet = "Item";
        attribute :>> sourceRow = 136;
    }
    item trace_5d798f7c3a5c4032 : TraceRecord {
        attribute :>> elementId = "PORTTYPE::PT-STA-024";
        attribute :>> sourceFile = "Rail_MBSE_Function_Interface_v1_final.xlsx";
        attribute :>> sourceSheet = "Item";
        attribute :>> sourceRow = 136;
    }
    item trace_66d6aa810a495dff : TraceRecord {
        attribute :>> elementId = "INTERFACETYPE::IF-STA-024";
        attribute :>> sourceFile = "Rail_MBSE_Function_Interface_v1_final.xlsx";
        attribute :>> sourceSheet = "Item";
        attribute :>> sourceRow = 136;
    }
    item trace_b8bb9e51c359815a : TraceRecord {
        attribute :>> elementId = "ITEM::ITM-STA-025";
        attribute :>> sourceFile = "Rail_MBSE_Function_Interface_v1_final.xlsx";
        attribute :>> sourceSheet = "Item";
        attribute :>> sourceRow = 137;
    }
    item trace_02c1c3bd14a3e6f7 : TraceRecord {
        attribute :>> elementId = "PORTTYPE::PT-STA-025";
        attribute :>> sourceFile = "Rail_MBSE_Function_Interface_v1_final.xlsx";
        attribute :>> sourceSheet = "Item";
        attribute :>> sourceRow = 137;
    }
    item trace_93f5ebc12675b775 : TraceRecord {
        attribute :>> elementId = "INTERFACETYPE::IF-STA-025";
        attribute :>> sourceFile = "Rail_MBSE_Function_Interface_v1_final.xlsx";
        attribute :>> sourceSheet = "Item";
        attribute :>> sourceRow = 137;
    }
    item trace_be93e764a4100e7e : TraceRecord {
        attribute :>> elementId = "ITEM::ITM-STA-026";
        attribute :>> sourceFile = "Rail_MBSE_Function_Interface_v1_final.xlsx";
        attribute :>> sourceSheet = "Item";
        attribute :>> sourceRow = 138;
    }
    item trace_f724cf007db26091 : TraceRecord {
        attribute :>> elementId = "PORTTYPE::PT-STA-026";
        attribute :>> sourceFile = "Rail_MBSE_Function_Interface_v1_final.xlsx";
        attribute :>> sourceSheet = "Item";
        attribute :>> sourceRow = 138;
    }
    item trace_3320ab92fc6aa514 : TraceRecord {
        attribute :>> elementId = "INTERFACETYPE::IF-STA-026";
        attribute :>> sourceFile = "Rail_MBSE_Function_Interface_v1_final.xlsx";
        attribute :>> sourceSheet = "Item";
        attribute :>> sourceRow = 138;
    }
    item trace_2025f1263aa02f7f : TraceRecord {
        attribute :>> elementId = "ITEM::ITM-STA-027";
        attribute :>> sourceFile = "Rail_MBSE_Function_Interface_v1_final.xlsx";
        attribute :>> sourceSheet = "Item";
        attribute :>> sourceRow = 139;
    }
    item trace_ccfaea477a9f5b4c : TraceRecord {
        attribute :>> elementId = "PORTTYPE::PT-STA-027";
        attribute :>> sourceFile = "Rail_MBSE_Function_Interface_v1_final.xlsx";
        attribute :>> sourceSheet = "Item";
        attribute :>> sourceRow = 139;
    }
    item trace_c5ef8fd258728f57 : TraceRecord {
        attribute :>> elementId = "INTERFACETYPE::IF-STA-027";
        attribute :>> sourceFile = "Rail_MBSE_Function_Interface_v1_final.xlsx";
        attribute :>> sourceSheet = "Item";
        attribute :>> sourceRow = 139;
    }
    item trace_ae5ffd60404bdfe0 : TraceRecord {
        attribute :>> elementId = "ITEM::ITM-STA-028";
        attribute :>> sourceFile = "Rail_MBSE_Function_Interface_v1_final.xlsx";
        attribute :>> sourceSheet = "Item";
        attribute :>> sourceRow = 140;
    }
    item trace_e0b396f09c9d1f94 : TraceRecord {
        attribute :>> elementId = "PORTTYPE::PT-STA-028";
        attribute :>> sourceFile = "Rail_MBSE_Function_Interface_v1_final.xlsx";
        attribute :>> sourceSheet = "Item";
        attribute :>> sourceRow = 140;
    }
    item trace_876f3d7ecac8c13a : TraceRecord {
        attribute :>> elementId = "INTERFACETYPE::IF-STA-028";
        attribute :>> sourceFile = "Rail_MBSE_Function_Interface_v1_final.xlsx";
        attribute :>> sourceSheet = "Item";
        attribute :>> sourceRow = 140;
    }
    item trace_bf111685a04a40bd : TraceRecord {
        attribute :>> elementId = "ITEM::ITM-STA-029";
        attribute :>> sourceFile = "Rail_MBSE_Function_Interface_v1_final.xlsx";
        attribute :>> sourceSheet = "Item";
        attribute :>> sourceRow = 141;
    }
    item trace_60a199061a97fadc : TraceRecord {
        attribute :>> elementId = "PORTTYPE::PT-STA-029";
        attribute :>> sourceFile = "Rail_MBSE_Function_Interface_v1_final.xlsx";
        attribute :>> sourceSheet = "Item";
        attribute :>> sourceRow = 141;
    }
    item trace_252a39105de679a0 : TraceRecord {
        attribute :>> elementId = "INTERFACETYPE::IF-STA-029";
        attribute :>> sourceFile = "Rail_MBSE_Function_Interface_v1_final.xlsx";
        attribute :>> sourceSheet = "Item";
        attribute :>> sourceRow = 141;
    }
    item trace_8b122088c419e31c : TraceRecord {
        attribute :>> elementId = "ITEM::ITM-STA-030";
        attribute :>> sourceFile = "Rail_MBSE_Function_Interface_v1_final.xlsx";
        attribute :>> sourceSheet = "Item";
        attribute :>> sourceRow = 142;
    }
    item trace_c988b3b1451bdbec : TraceRecord {
        attribute :>> elementId = "PORTTYPE::PT-STA-030";
        attribute :>> sourceFile = "Rail_MBSE_Function_Interface_v1_final.xlsx";
        attribute :>> sourceSheet = "Item";
        attribute :>> sourceRow = 142;
    }
    item trace_358e776424ba01d0 : TraceRecord {
        attribute :>> elementId = "INTERFACETYPE::IF-STA-030";
        attribute :>> sourceFile = "Rail_MBSE_Function_Interface_v1_final.xlsx";
        attribute :>> sourceSheet = "Item";
        attribute :>> sourceRow = 142;
    }
    item trace_f146f0f679270fe1 : TraceRecord {
        attribute :>> elementId = "ITEM::ITM-STA-031";
        attribute :>> sourceFile = "Rail_MBSE_Function_Interface_v1_final.xlsx";
        attribute :>> sourceSheet = "Item";
        attribute :>> sourceRow = 143;
    }
    item trace_5aa447464c2c0403 : TraceRecord {
        attribute :>> elementId = "PORTTYPE::PT-STA-031";
        attribute :>> sourceFile = "Rail_MBSE_Function_Interface_v1_final.xlsx";
        attribute :>> sourceSheet = "Item";
        attribute :>> sourceRow = 143;
    }
    item trace_d8175bf68ee86bc5 : TraceRecord {
        attribute :>> elementId = "INTERFACETYPE::IF-STA-031";
        attribute :>> sourceFile = "Rail_MBSE_Function_Interface_v1_final.xlsx";
        attribute :>> sourceSheet = "Item";
        attribute :>> sourceRow = 143;
    }
    item trace_6652a3dd054d2bf4 : TraceRecord {
        attribute :>> elementId = "ITEM::ITM-STA-032";
        attribute :>> sourceFile = "Rail_MBSE_Function_Interface_v1_final.xlsx";
        attribute :>> sourceSheet = "Item";
        attribute :>> sourceRow = 144;
    }
    item trace_d4d77eab66539a78 : TraceRecord {
        attribute :>> elementId = "PORTTYPE::PT-STA-032";
        attribute :>> sourceFile = "Rail_MBSE_Function_Interface_v1_final.xlsx";
        attribute :>> sourceSheet = "Item";
        attribute :>> sourceRow = 144;
    }
    item trace_6ed32f315f32b296 : TraceRecord {
        attribute :>> elementId = "INTERFACETYPE::IF-STA-032";
        attribute :>> sourceFile = "Rail_MBSE_Function_Interface_v1_final.xlsx";
        attribute :>> sourceSheet = "Item";
        attribute :>> sourceRow = 144;
    }
    item trace_98c4403c251b7414 : TraceRecord {
        attribute :>> elementId = "ITEM::ITM-STA-033";
        attribute :>> sourceFile = "Rail_MBSE_Function_Interface_v1_final.xlsx";
        attribute :>> sourceSheet = "Item";
        attribute :>> sourceRow = 145;
    }
    item trace_b6177ef888838cda : TraceRecord {
        attribute :>> elementId = "PORTTYPE::PT-STA-033";
        attribute :>> sourceFile = "Rail_MBSE_Function_Interface_v1_final.xlsx";
        attribute :>> sourceSheet = "Item";
        attribute :>> sourceRow = 145;
    }
    item trace_3b09d41839a03cf2 : TraceRecord {
        attribute :>> elementId = "INTERFACETYPE::IF-STA-033";
        attribute :>> sourceFile = "Rail_MBSE_Function_Interface_v1_final.xlsx";
        attribute :>> sourceSheet = "Item";
        attribute :>> sourceRow = 145;
    }
    item trace_b2ae5270f04ab2c6 : TraceRecord {
        attribute :>> elementId = "ITEM::ITM-STA-034";
        attribute :>> sourceFile = "Rail_MBSE_Function_Interface_v1_final.xlsx";
        attribute :>> sourceSheet = "Item";
        attribute :>> sourceRow = 146;
    }
    item trace_49e8cbf108c192c6 : TraceRecord {
        attribute :>> elementId = "PORTTYPE::PT-STA-034";
        attribute :>> sourceFile = "Rail_MBSE_Function_Interface_v1_final.xlsx";
        attribute :>> sourceSheet = "Item";
        attribute :>> sourceRow = 146;
    }
    item trace_7edc322ddc9eefe6 : TraceRecord {
        attribute :>> elementId = "INTERFACETYPE::IF-STA-034";
        attribute :>> sourceFile = "Rail_MBSE_Function_Interface_v1_final.xlsx";
        attribute :>> sourceSheet = "Item";
        attribute :>> sourceRow = 146;
    }
    item trace_4c8b08e2907ac89e : TraceRecord {
        attribute :>> elementId = "ITEM::ITM-STA-035";
        attribute :>> sourceFile = "Rail_MBSE_Function_Interface_v1_final.xlsx";
        attribute :>> sourceSheet = "Item";
        attribute :>> sourceRow = 147;
    }
    item trace_bd757c92072ff247 : TraceRecord {
        attribute :>> elementId = "PORTTYPE::PT-STA-035";
        attribute :>> sourceFile = "Rail_MBSE_Function_Interface_v1_final.xlsx";
        attribute :>> sourceSheet = "Item";
        attribute :>> sourceRow = 147;
    }
    item trace_78c826f41aa017fc : TraceRecord {
        attribute :>> elementId = "INTERFACETYPE::IF-STA-035";
        attribute :>> sourceFile = "Rail_MBSE_Function_Interface_v1_final.xlsx";
        attribute :>> sourceSheet = "Item";
        attribute :>> sourceRow = 147;
    }
    item trace_28a3a6378c895795 : TraceRecord {
        attribute :>> elementId = "ITEM::ITM-STA-036";
        attribute :>> sourceFile = "Rail_MBSE_Function_Interface_v1_final.xlsx";
        attribute :>> sourceSheet = "Item";
        attribute :>> sourceRow = 148;
    }
    item trace_1251b066e3792748 : TraceRecord {
        attribute :>> elementId = "PORTTYPE::PT-STA-036";
        attribute :>> sourceFile = "Rail_MBSE_Function_Interface_v1_final.xlsx";
        attribute :>> sourceSheet = "Item";
        attribute :>> sourceRow = 148;
    }
    item trace_7e3b1505f90fbb2d : TraceRecord {
        attribute :>> elementId = "INTERFACETYPE::IF-STA-036";
        attribute :>> sourceFile = "Rail_MBSE_Function_Interface_v1_final.xlsx";
        attribute :>> sourceSheet = "Item";
        attribute :>> sourceRow = 148;
    }
    item trace_8ee7c79c0fe26b93 : TraceRecord {
        attribute :>> elementId = "PORT::3111::轮轨纵向机械作用端口::ITM-PHY-006::双向物理";
        attribute :>> sourceFile = "Rail_MBSE_Function_Interface_v1_final.xlsx";
        attribute :>> sourceSheet = "Interface";
        attribute :>> sourceRow = 5;
    }
    item trace_f0350fc816a551ff : TraceRecord {
        attribute :>> elementId = "PORT::3111::轮轴旋转机械能端口::ITM-PHY-005::双向物理";
        attribute :>> sourceFile = "Rail_MBSE_Function_Interface_v1_final.xlsx";
        attribute :>> sourceSheet = "Interface";
        attribute :>> sourceRow = 6;
    }
    item trace_6917242b1f7fc50f : TraceRecord {
        attribute :>> elementId = "PORT::3112::传动段旋转机械能端口::ITM-PHY-005::双向物理";
        attribute :>> sourceFile = "Rail_MBSE_Function_Interface_v1_final.xlsx";
        attribute :>> sourceSheet = "Interface";
        attribute :>> sourceRow = 7;
    }
    item trace_c530418a51140052 : TraceRecord {
        attribute :>> elementId = "PORT::3112::轮对段旋转机械能端口::ITM-PHY-005::双向物理";
        attribute :>> sourceFile = "Rail_MBSE_Function_Interface_v1_final.xlsx";
        attribute :>> sourceSheet = "Interface";
        attribute :>> sourceRow = 8;
    }
    item trace_6464b6253314b208 : TraceRecord {
        attribute :>> elementId = "PORT::3121::低速轴旋转机械能端口::ITM-PHY-005::双向物理";
        attribute :>> sourceFile = "Rail_MBSE_Function_Interface_v1_final.xlsx";
        attribute :>> sourceSheet = "Interface";
        attribute :>> sourceRow = 9;
    }
    item trace_fdcd27ee9b0a936f : TraceRecord {
        attribute :>> elementId = "PORT::3121::高速轴旋转机械能端口::ITM-PHY-005::双向物理";
        attribute :>> sourceFile = "Rail_MBSE_Function_Interface_v1_final.xlsx";
        attribute :>> sourceSheet = "Interface";
        attribute :>> sourceRow = 10;
    }
    item trace_06d152ddc255f2eb : TraceRecord {
        attribute :>> elementId = "PORT::3131::摩擦制动机械作用端口::ITM-PHY-007::双向物理";
        attribute :>> sourceFile = "Rail_MBSE_Function_Interface_v1_final.xlsx";
        attribute :>> sourceSheet = "Interface";
        attribute :>> sourceRow = 11;
    }
    item trace_ec78c2de89f1a17c : TraceRecord {
        attribute :>> elementId = "PORT::3131::热能_热流端口::ITM-PHY-013::双向物理";
        attribute :>> sourceFile = "Rail_MBSE_Function_Interface_v1_final.xlsx";
        attribute :>> sourceSheet = "Interface";
        attribute :>> sourceRow = 12;
    }
    item trace_6dfc099101cb436c : TraceRecord {
        attribute :>> elementId = "PORT::3132::摩擦制动机械作用端口::ITM-PHY-007::双向物理";
        attribute :>> sourceFile = "Rail_MBSE_Function_Interface_v1_final.xlsx";
        attribute :>> sourceSheet = "Interface";
        attribute :>> sourceRow = 13;
    }
    item trace_6069e8d0fbf298c5 : TraceRecord {
        attribute :>> elementId = "PORT::3132::热能_热流端口::ITM-PHY-013::双向物理";
        attribute :>> sourceFile = "Rail_MBSE_Function_Interface_v1_final.xlsx";
        attribute :>> sourceSheet = "Interface";
        attribute :>> sourceRow = 14;
    }
    item trace_7738143ff23b3321 : TraceRecord {
        attribute :>> elementId = "PORT::3133::摩擦制动机械作用端口::ITM-PHY-007::双向物理";
        attribute :>> sourceFile = "Rail_MBSE_Function_Interface_v1_final.xlsx";
        attribute :>> sourceSheet = "Interface";
        attribute :>> sourceRow = 15;
    }
    item trace_24fa6cb520a8e2e2 : TraceRecord {
        attribute :>> elementId = "PORT::3133::热能_热流端口::ITM-PHY-013::双向物理";
        attribute :>> sourceFile = "Rail_MBSE_Function_Interface_v1_final.xlsx";
        attribute :>> sourceSheet = "Interface";
        attribute :>> sourceRow = 16;
    }
    item trace_aa7691c6f81e4771 : TraceRecord {
        attribute :>> elementId = "PORT::3511::第一连接面旋转机械能端口::ITM-PHY-005::双向物理";
        attribute :>> sourceFile = "Rail_MBSE_Function_Interface_v1_final.xlsx";
        attribute :>> sourceSheet = "Interface";
        attribute :>> sourceRow = 17;
    }
    item trace_813a305545723d57 : TraceRecord {
        attribute :>> elementId = "PORT::3511::第二连接面旋转机械能端口::ITM-PHY-005::双向物理";
        attribute :>> sourceFile = "Rail_MBSE_Function_Interface_v1_final.xlsx";
        attribute :>> sourceSheet = "Interface";
        attribute :>> sourceRow = 18;
    }
    item trace_970ef7da9f850ce1 : TraceRecord {
        attribute :>> elementId = "PORT::3512::第一连接面旋转机械能端口::ITM-PHY-005::双向物理";
        attribute :>> sourceFile = "Rail_MBSE_Function_Interface_v1_final.xlsx";
        attribute :>> sourceSheet = "Interface";
        attribute :>> sourceRow = 19;
    }
    item trace_c455741f6ca5a597 : TraceRecord {
        attribute :>> elementId = "PORT::3512::第二连接面旋转机械能端口::ITM-PHY-005::双向物理";
        attribute :>> sourceFile = "Rail_MBSE_Function_Interface_v1_final.xlsx";
        attribute :>> sourceSheet = "Interface";
        attribute :>> sourceRow = 20;
    }
    item trace_b12dc4cc17618821 : TraceRecord {
        attribute :>> elementId = "PORT::3514::第一轴端旋转机械能端口::ITM-PHY-005::双向物理";
        attribute :>> sourceFile = "Rail_MBSE_Function_Interface_v1_final.xlsx";
        attribute :>> sourceSheet = "Interface";
        attribute :>> sourceRow = 21;
    }
    item trace_4569aa8f56963dc6 : TraceRecord {
        attribute :>> elementId = "PORT::3514::第二轴端旋转机械能端口::ITM-PHY-005::双向物理";
        attribute :>> sourceFile = "Rail_MBSE_Function_Interface_v1_final.xlsx";
        attribute :>> sourceSheet = "Interface";
        attribute :>> sourceRow = 22;
    }
    item trace_4ddc6037e5eea6fc : TraceRecord {
        attribute :>> elementId = "PORT::3641::旋转机械能端口::ITM-PHY-005::双向物理";
        attribute :>> sourceFile = "Rail_MBSE_Function_Interface_v1_final.xlsx";
        attribute :>> sourceSheet = "Interface";
        attribute :>> sourceRow = 23;
    }
    item trace_0875fbdf10c0dc7e : TraceRecord {
        attribute :>> elementId = "PORT::3641::轴端角速度输出::ITM-MEA-002::输出";
        attribute :>> sourceFile = "Rail_MBSE_Function_Interface_v1_final.xlsx";
        attribute :>> sourceSheet = "Interface";
        attribute :>> sourceRow = 24;
    }
    item trace_48ddc723a7d58137 : TraceRecord {
        attribute :>> elementId = "PORT::3643::旋转机械能端口::ITM-PHY-005::双向物理";
        attribute :>> sourceFile = "Rail_MBSE_Function_Interface_v1_final.xlsx";
        attribute :>> sourceSheet = "Interface";
        attribute :>> sourceRow = 25;
    }
    item trace_213dbf9f44535a8a : TraceRecord {
        attribute :>> elementId = "PORT::3643::齿轮箱转速输出::ITM-MEA-003::输出";
        attribute :>> sourceFile = "Rail_MBSE_Function_Interface_v1_final.xlsx";
        attribute :>> sourceSheet = "Interface";
        attribute :>> sourceRow = 26;
    }
    item trace_af1c1b2c65382775 : TraceRecord {
        attribute :>> elementId = "PORT::3644::旋转机械能端口::ITM-PHY-005::双向物理";
        attribute :>> sourceFile = "Rail_MBSE_Function_Interface_v1_final.xlsx";
        attribute :>> sourceSheet = "Interface";
        attribute :>> sourceRow = 27;
    }
    item trace_08c271db56ce8427 : TraceRecord {
        attribute :>> elementId = "PORT::3644::牵引电机转速输出::ITM-MEA-004::输出";
        attribute :>> sourceFile = "Rail_MBSE_Function_Interface_v1_final.xlsx";
        attribute :>> sourceSheet = "Interface";
        attribute :>> sourceRow = 28;
    }
    item trace_ad36be2404e763eb : TraceRecord {
        attribute :>> elementId = "PORT::3811::低压控制电能端口::ITM-PHY-015::双向物理";
        attribute :>> sourceFile = "Rail_MBSE_Function_Interface_v1_final.xlsx";
        attribute :>> sourceSheet = "Interface";
        attribute :>> sourceRow = 29;
    }
    item trace_3a8ce42fcde5acd8 : TraceRecord {
        attribute :>> elementId = "PORT::3811::撒砂执行指令输出::ITM-CMD-032::输出";
        attribute :>> sourceFile = "Rail_MBSE_Function_Interface_v1_final.xlsx";
        attribute :>> sourceSheet = "Interface";
        attribute :>> sourceRow = 30;
    }
    item trace_aa4dbc7721f19e23 : TraceRecord {
        attribute :>> elementId = "PORT::3811::撒砂状态输出::ITM-STA-012::输出";
        attribute :>> sourceFile = "Rail_MBSE_Function_Interface_v1_final.xlsx";
        attribute :>> sourceSheet = "Interface";
        attribute :>> sourceRow = 31;
    }
    item trace_81d4e1a7092e0653 : TraceRecord {
        attribute :>> elementId = "PORT::3811::撒砂请求输入::ITM-CMD-024::输入";
        attribute :>> sourceFile = "Rail_MBSE_Function_Interface_v1_final.xlsx";
        attribute :>> sourceSheet = "Interface";
        attribute :>> sourceRow = 32;
    }
    item trace_3f7e961856b812d2 : TraceRecord {
        attribute :>> elementId = "PORT::3813::主风压缩空气端口::ITM-PHY-008::双向物理";
        attribute :>> sourceFile = "Rail_MBSE_Function_Interface_v1_final.xlsx";
        attribute :>> sourceSheet = "Interface";
        attribute :>> sourceRow = 33;
    }
    item trace_d951497aaa9989f0 : TraceRecord {
        attribute :>> elementId = "PORT::3813::撒砂执行指令输入::ITM-CMD-032::输入";
        attribute :>> sourceFile = "Rail_MBSE_Function_Interface_v1_final.xlsx";
        attribute :>> sourceSheet = "Interface";
        attribute :>> sourceRow = 34;
    }
    item trace_3344f097f2d78315 : TraceRecord {
        attribute :>> elementId = "PORT::3813::撒砂状态输出::ITM-STA-012::输出";
        attribute :>> sourceFile = "Rail_MBSE_Function_Interface_v1_final.xlsx";
        attribute :>> sourceSheet = "Interface";
        attribute :>> sourceRow = 35;
    }
    item trace_c843e562c7ec3ed9 : TraceRecord {
        attribute :>> elementId = "PORT::3813::砂流端口::ITM-PHY-012::双向物理";
        attribute :>> sourceFile = "Rail_MBSE_Function_Interface_v1_final.xlsx";
        attribute :>> sourceSheet = "Interface";
        attribute :>> sourceRow = 36;
    }
    item trace_43d42f25a744fe07 : TraceRecord {
        attribute :>> elementId = "PORT::3814::砂流端口::ITM-PHY-012::双向物理";
        attribute :>> sourceFile = "Rail_MBSE_Function_Interface_v1_final.xlsx";
        attribute :>> sourceSheet = "Interface";
        attribute :>> sourceRow = 37;
    }
    item trace_ca65ceda639dfc7a : TraceRecord {
        attribute :>> elementId = "PORT::4111::导流端高压交流电能端口::ITM-PHY-001::双向物理";
        attribute :>> sourceFile = "Rail_MBSE_Function_Interface_v1_final.xlsx";
        attribute :>> sourceSheet = "Interface";
        attribute :>> sourceRow = 38;
    }
    item trace_695b20573c740008 : TraceRecord {
        attribute :>> elementId = "PORT::4111::接触面高压交流电能端口::ITM-PHY-001::双向物理";
        attribute :>> sourceFile = "Rail_MBSE_Function_Interface_v1_final.xlsx";
        attribute :>> sourceSheet = "Interface";
        attribute :>> sourceRow = 39;
    }
    item trace_d6a2171160c4b693 : TraceRecord {
        attribute :>> elementId = "PORT::411C::低压控制电能端口::ITM-PHY-015::双向物理";
        attribute :>> sourceFile = "Rail_MBSE_Function_Interface_v1_final.xlsx";
        attribute :>> sourceSheet = "Interface";
        attribute :>> sourceRow = 40;
    }
    item trace_201c13a158f19a88 : TraceRecord {
        attribute :>> elementId = "PORT::411C::受电弓控制指令输入::ITM-CMD-018::输入";
        attribute :>> sourceFile = "Rail_MBSE_Function_Interface_v1_final.xlsx";
        attribute :>> sourceSheet = "Interface";
        attribute :>> sourceRow = 41;
    }
    item trace_72d2eed2608e1b56 : TraceRecord {
        attribute :>> elementId = "PORT::411C::受电弓状态输出::ITM-STA-015::输出";
        attribute :>> sourceFile = "Rail_MBSE_Function_Interface_v1_final.xlsx";
        attribute :>> sourceSheet = "Interface";
        attribute :>> sourceRow = 42;
    }
    item trace_7f443c4ab63f77d2 : TraceRecord {
        attribute :>> elementId = "PORT::411C::高压系统故障状态输出::ITM-STA-016::输出";
        attribute :>> sourceFile = "Rail_MBSE_Function_Interface_v1_final.xlsx";
        attribute :>> sourceSheet = "Interface";
        attribute :>> sourceRow = 43;
    }
    item trace_d35e3f96846f95a6 : TraceRecord {
        attribute :>> elementId = "PORT::4121::受流端直流牵引供电电能端口::ITM-PHY-002::双向物理";
        attribute :>> sourceFile = "Rail_MBSE_Function_Interface_v1_final.xlsx";
        attribute :>> sourceSheet = "Interface";
        attribute :>> sourceRow = 44;
    }
    item trace_3a0861f1892e9d5f : TraceRecord {
        attribute :>> elementId = "PORT::4121::导流端直流牵引供电电能端口::ITM-PHY-002::双向物理";
        attribute :>> sourceFile = "Rail_MBSE_Function_Interface_v1_final.xlsx";
        attribute :>> sourceSheet = "Interface";
        attribute :>> sourceRow = 45;
    }
    item trace_ee92cd728b152a90 : TraceRecord {
        attribute :>> elementId = "PORT::4211::出线侧高压交流电能端口::ITM-PHY-001::双向物理";
        attribute :>> sourceFile = "Rail_MBSE_Function_Interface_v1_final.xlsx";
        attribute :>> sourceSheet = "Interface";
        attribute :>> sourceRow = 46;
    }
    item trace_bba7ece236be8f3c : TraceRecord {
        attribute :>> elementId = "PORT::4211::进线侧高压交流电能端口::ITM-PHY-001::双向物理";
        attribute :>> sourceFile = "Rail_MBSE_Function_Interface_v1_final.xlsx";
        attribute :>> sourceSheet = "Interface";
        attribute :>> sourceRow = 47;
    }
    item trace_17bc6a2a377dffab : TraceRecord {
        attribute :>> elementId = "PORT::4211::高压断路器指令输入::ITM-CMD-016::输入";
        attribute :>> sourceFile = "Rail_MBSE_Function_Interface_v1_final.xlsx";
        attribute :>> sourceSheet = "Interface";
        attribute :>> sourceRow = 48;
    }
    item trace_5301bf8bda8fba16 : TraceRecord {
        attribute :>> elementId = "PORT::4211::高压断路器状态输出::ITM-STA-013::输出";
        attribute :>> sourceFile = "Rail_MBSE_Function_Interface_v1_final.xlsx";
        attribute :>> sourceSheet = "Interface";
        attribute :>> sourceRow = 49;
    }
    item trace_5fec968d70e06b36 : TraceRecord {
        attribute :>> elementId = "PORT::4211::高压系统故障状态输出::ITM-STA-016::输出";
        attribute :>> sourceFile = "Rail_MBSE_Function_Interface_v1_final.xlsx";
        attribute :>> sourceSheet = "Interface";
        attribute :>> sourceRow = 50;
    }
    item trace_0ce11b1eb6ca7ee8 : TraceRecord {
        attribute :>> elementId = "PORT::4212::出线侧直流牵引供电电能端口::ITM-PHY-002::双向物理";
        attribute :>> sourceFile = "Rail_MBSE_Function_Interface_v1_final.xlsx";
        attribute :>> sourceSheet = "Interface";
        attribute :>> sourceRow = 51;
    }
    item trace_e1689d643b97d378 : TraceRecord {
        attribute :>> elementId = "PORT::4212::出线侧高压交流电能端口::ITM-PHY-001::双向物理";
        attribute :>> sourceFile = "Rail_MBSE_Function_Interface_v1_final.xlsx";
        attribute :>> sourceSheet = "Interface";
        attribute :>> sourceRow = 52;
    }
    item trace_e344333f6e011283 : TraceRecord {
        attribute :>> elementId = "PORT::4212::进线侧直流牵引供电电能端口::ITM-PHY-002::双向物理";
        attribute :>> sourceFile = "Rail_MBSE_Function_Interface_v1_final.xlsx";
        attribute :>> sourceSheet = "Interface";
        attribute :>> sourceRow = 53;
    }
    item trace_4b65d610848833a3 : TraceRecord {
        attribute :>> elementId = "PORT::4212::进线侧高压交流电能端口::ITM-PHY-001::双向物理";
        attribute :>> sourceFile = "Rail_MBSE_Function_Interface_v1_final.xlsx";
        attribute :>> sourceSheet = "Interface";
        attribute :>> sourceRow = 54;
    }
    item trace_a29d16c43fc8d044 : TraceRecord {
        attribute :>> elementId = "PORT::4212::高压隔离开关指令输入::ITM-CMD-017::输入";
        attribute :>> sourceFile = "Rail_MBSE_Function_Interface_v1_final.xlsx";
        attribute :>> sourceSheet = "Interface";
        attribute :>> sourceRow = 55;
    }
    item trace_62a902ccb2d5edf3 : TraceRecord {
        attribute :>> elementId = "PORT::4212::高压隔离开关状态输出::ITM-STA-014::输出";
        attribute :>> sourceFile = "Rail_MBSE_Function_Interface_v1_final.xlsx";
        attribute :>> sourceSheet = "Interface";
        attribute :>> sourceRow = 56;
    }
    item trace_3e2b71c6b8d79136 : TraceRecord {
        attribute :>> elementId = "PORT::4235::高压交流电能端口::ITM-PHY-001::双向物理";
        attribute :>> sourceFile = "Rail_MBSE_Function_Interface_v1_final.xlsx";
        attribute :>> sourceSheet = "Interface";
        attribute :>> sourceRow = 57;
    }
    item trace_6fea4b377f978aac : TraceRecord {
        attribute :>> elementId = "PORT::4235::高压线路电压输出::ITM-MEA-005::输出";
        attribute :>> sourceFile = "Rail_MBSE_Function_Interface_v1_final.xlsx";
        attribute :>> sourceSheet = "Interface";
        attribute :>> sourceRow = 58;
    }
    item trace_bb6f3fee449fd865 : TraceRecord {
        attribute :>> elementId = "PORT::4236::第一测量端高压交流电能端口::ITM-PHY-001::双向物理";
        attribute :>> sourceFile = "Rail_MBSE_Function_Interface_v1_final.xlsx";
        attribute :>> sourceSheet = "Interface";
        attribute :>> sourceRow = 59;
    }
    item trace_78e99abb7d77c156 : TraceRecord {
        attribute :>> elementId = "PORT::4236::第二测量端高压交流电能端口::ITM-PHY-001::双向物理";
        attribute :>> sourceFile = "Rail_MBSE_Function_Interface_v1_final.xlsx";
        attribute :>> sourceSheet = "Interface";
        attribute :>> sourceRow = 60;
    }
    item trace_9107465175683792 : TraceRecord {
        attribute :>> elementId = "PORT::4236::高压线路电流输出::ITM-MEA-006::输出";
        attribute :>> sourceFile = "Rail_MBSE_Function_Interface_v1_final.xlsx";
        attribute :>> sourceSheet = "Interface";
        attribute :>> sourceRow = 61;
    }
    item trace_dc173bda6489186d : TraceRecord {
        attribute :>> elementId = "PORT::4238::低压控制电能端口::ITM-PHY-015::双向物理";
        attribute :>> sourceFile = "Rail_MBSE_Function_Interface_v1_final.xlsx";
        attribute :>> sourceSheet = "Interface";
        attribute :>> sourceRow = 62;
    }
    item trace_71811e4b68798212 : TraceRecord {
        attribute :>> elementId = "PORT::4238::受电弓控制指令输入::ITM-CMD-018::输入";
        attribute :>> sourceFile = "Rail_MBSE_Function_Interface_v1_final.xlsx";
        attribute :>> sourceSheet = "Interface";
        attribute :>> sourceRow = 63;
    }
    item trace_9744a4b3a255a6e8 : TraceRecord {
        attribute :>> elementId = "PORT::4238::受电弓控制指令输出::ITM-CMD-018::输出";
        attribute :>> sourceFile = "Rail_MBSE_Function_Interface_v1_final.xlsx";
        attribute :>> sourceSheet = "Interface";
        attribute :>> sourceRow = 64;
    }
    item trace_d9d25dfbac32d1e3 : TraceRecord {
        attribute :>> elementId = "PORT::4238::受电弓状态输入::ITM-STA-015::输入";
        attribute :>> sourceFile = "Rail_MBSE_Function_Interface_v1_final.xlsx";
        attribute :>> sourceSheet = "Interface";
        attribute :>> sourceRow = 65;
    }
    item trace_86fe03530d5b3c05 : TraceRecord {
        attribute :>> elementId = "PORT::4238::受电弓状态输出::ITM-STA-015::输出";
        attribute :>> sourceFile = "Rail_MBSE_Function_Interface_v1_final.xlsx";
        attribute :>> sourceSheet = "Interface";
        attribute :>> sourceRow = 66;
    }
    item trace_d6b968957e3167c7 : TraceRecord {
        attribute :>> elementId = "PORT::4238::高压断路器指令输入::ITM-CMD-016::输入";
        attribute :>> sourceFile = "Rail_MBSE_Function_Interface_v1_final.xlsx";
        attribute :>> sourceSheet = "Interface";
        attribute :>> sourceRow = 67;
    }
    item trace_65aacc4600de3990 : TraceRecord {
        attribute :>> elementId = "PORT::4238::高压断路器指令输出::ITM-CMD-016::输出";
        attribute :>> sourceFile = "Rail_MBSE_Function_Interface_v1_final.xlsx";
        attribute :>> sourceSheet = "Interface";
        attribute :>> sourceRow = 68;
    }
    item trace_b26de8005dff4962 : TraceRecord {
        attribute :>> elementId = "PORT::4238::高压断路器状态输入::ITM-STA-013::输入";
        attribute :>> sourceFile = "Rail_MBSE_Function_Interface_v1_final.xlsx";
        attribute :>> sourceSheet = "Interface";
        attribute :>> sourceRow = 69;
    }
    item trace_0674d2b80a6a72da : TraceRecord {
        attribute :>> elementId = "PORT::4238::高压断路器状态输出::ITM-STA-013::输出";
        attribute :>> sourceFile = "Rail_MBSE_Function_Interface_v1_final.xlsx";
        attribute :>> sourceSheet = "Interface";
        attribute :>> sourceRow = 70;
    }
    item trace_11b7e7965ec2e386 : TraceRecord {
        attribute :>> elementId = "PORT::4238::高压系统故障状态输入::ITM-STA-016::输入";
        attribute :>> sourceFile = "Rail_MBSE_Function_Interface_v1_final.xlsx";
        attribute :>> sourceSheet = "Interface";
        attribute :>> sourceRow = 71;
    }
    item trace_9458944450b0dd4c : TraceRecord {
        attribute :>> elementId = "PORT::4238::高压系统故障状态输出::ITM-STA-016::输出";
        attribute :>> sourceFile = "Rail_MBSE_Function_Interface_v1_final.xlsx";
        attribute :>> sourceSheet = "Interface";
        attribute :>> sourceRow = 72;
    }
    item trace_c88ddcdfe3b55c9e : TraceRecord {
        attribute :>> elementId = "PORT::4238::高压线路电压输入::ITM-MEA-005::输入";
        attribute :>> sourceFile = "Rail_MBSE_Function_Interface_v1_final.xlsx";
        attribute :>> sourceSheet = "Interface";
        attribute :>> sourceRow = 73;
    }
    item trace_5576b5e0dbb912ba : TraceRecord {
        attribute :>> elementId = "PORT::4238::高压线路电压输出::ITM-MEA-005::输出";
        attribute :>> sourceFile = "Rail_MBSE_Function_Interface_v1_final.xlsx";
        attribute :>> sourceSheet = "Interface";
        attribute :>> sourceRow = 74;
    }
    item trace_afb7b0997d28e7cb : TraceRecord {
        attribute :>> elementId = "PORT::4238::高压线路电流输入::ITM-MEA-006::输入";
        attribute :>> sourceFile = "Rail_MBSE_Function_Interface_v1_final.xlsx";
        attribute :>> sourceSheet = "Interface";
        attribute :>> sourceRow = 75;
    }
    item trace_c7dcc306b020116f : TraceRecord {
        attribute :>> elementId = "PORT::4238::高压线路电流输出::ITM-MEA-006::输出";
        attribute :>> sourceFile = "Rail_MBSE_Function_Interface_v1_final.xlsx";
        attribute :>> sourceSheet = "Interface";
        attribute :>> sourceRow = 76;
    }
    item trace_f6362be8ea9a501f : TraceRecord {
        attribute :>> elementId = "PORT::4238::高压隔离开关指令输入::ITM-CMD-017::输入";
        attribute :>> sourceFile = "Rail_MBSE_Function_Interface_v1_final.xlsx";
        attribute :>> sourceSheet = "Interface";
        attribute :>> sourceRow = 77;
    }
    item trace_ed1efa73e618c52f : TraceRecord {
        attribute :>> elementId = "PORT::4238::高压隔离开关指令输出::ITM-CMD-017::输出";
        attribute :>> sourceFile = "Rail_MBSE_Function_Interface_v1_final.xlsx";
        attribute :>> sourceSheet = "Interface";
        attribute :>> sourceRow = 78;
    }
    item trace_b46091b51fbac2ba : TraceRecord {
        attribute :>> elementId = "PORT::4238::高压隔离开关状态输入::ITM-STA-014::输入";
        attribute :>> sourceFile = "Rail_MBSE_Function_Interface_v1_final.xlsx";
        attribute :>> sourceSheet = "Interface";
        attribute :>> sourceRow = 79;
    }
    item trace_7fe2b8fd826583f2 : TraceRecord {
        attribute :>> elementId = "PORT::4238::高压隔离开关状态输出::ITM-STA-014::输出";
        attribute :>> sourceFile = "Rail_MBSE_Function_Interface_v1_final.xlsx";
        attribute :>> sourceSheet = "Interface";
        attribute :>> sourceRow = 80;
    }
    item trace_9c4bbbf0c73d853e : TraceRecord {
        attribute :>> elementId = "PORT::4239::低压控制电能端口::ITM-PHY-015::双向物理";
        attribute :>> sourceFile = "Rail_MBSE_Function_Interface_v1_final.xlsx";
        attribute :>> sourceSheet = "Interface";
        attribute :>> sourceRow = 81;
    }
    item trace_327ede77d6565c4b : TraceRecord {
        attribute :>> elementId = "PORT::4239::受电弓控制指令输出::ITM-CMD-018::输出";
        attribute :>> sourceFile = "Rail_MBSE_Function_Interface_v1_final.xlsx";
        attribute :>> sourceSheet = "Interface";
        attribute :>> sourceRow = 82;
    }
    item trace_f3be8ead57323593 : TraceRecord {
        attribute :>> elementId = "PORT::4239::受电弓状态输入::ITM-STA-015::输入";
        attribute :>> sourceFile = "Rail_MBSE_Function_Interface_v1_final.xlsx";
        attribute :>> sourceSheet = "Interface";
        attribute :>> sourceRow = 83;
    }
    item trace_a59e6c38c7d9e2cb : TraceRecord {
        attribute :>> elementId = "PORT::4239::线路频率输入::ITM-MEA-007::输入";
        attribute :>> sourceFile = "Rail_MBSE_Function_Interface_v1_final.xlsx";
        attribute :>> sourceSheet = "Interface";
        attribute :>> sourceRow = 84;
    }
    item trace_c9c4c887a8c7b2f0 : TraceRecord {
        attribute :>> elementId = "PORT::4239::高压安全回路状态输入::ITM-STA-024::输入";
        attribute :>> sourceFile = "Rail_MBSE_Function_Interface_v1_final.xlsx";
        attribute :>> sourceSheet = "Interface";
        attribute :>> sourceRow = 85;
    }
    item trace_e67f315619e85b76 : TraceRecord {
        attribute :>> elementId = "PORT::4239::高压断路器指令输出::ITM-CMD-016::输出";
        attribute :>> sourceFile = "Rail_MBSE_Function_Interface_v1_final.xlsx";
        attribute :>> sourceSheet = "Interface";
        attribute :>> sourceRow = 86;
    }
    item trace_1fd23591362c1d8d : TraceRecord {
        attribute :>> elementId = "PORT::4239::高压断路器状态输入::ITM-STA-013::输入";
        attribute :>> sourceFile = "Rail_MBSE_Function_Interface_v1_final.xlsx";
        attribute :>> sourceSheet = "Interface";
        attribute :>> sourceRow = 87;
    }
    item trace_390a7ebf7324c6d6 : TraceRecord {
        attribute :>> elementId = "PORT::4239::高压系统故障状态汇总输出::ITM-STA-016::输出";
        attribute :>> sourceFile = "Rail_MBSE_Function_Interface_v1_final.xlsx";
        attribute :>> sourceSheet = "Interface";
        attribute :>> sourceRow = 88;
    }
    item trace_be1480d12bc9092c : TraceRecord {
        attribute :>> elementId = "PORT::4239::高压系统故障状态采集输入::ITM-STA-016::输入";
        attribute :>> sourceFile = "Rail_MBSE_Function_Interface_v1_final.xlsx";
        attribute :>> sourceSheet = "Interface";
        attribute :>> sourceRow = 89;
    }
    item trace_2802b0f2f54a548a : TraceRecord {
        attribute :>> elementId = "PORT::4239::高压线路电压输入::ITM-MEA-005::输入";
        attribute :>> sourceFile = "Rail_MBSE_Function_Interface_v1_final.xlsx";
        attribute :>> sourceSheet = "Interface";
        attribute :>> sourceRow = 90;
    }
    item trace_1a7ff383166e59f0 : TraceRecord {
        attribute :>> elementId = "PORT::4239::高压线路电流输入::ITM-MEA-006::输入";
        attribute :>> sourceFile = "Rail_MBSE_Function_Interface_v1_final.xlsx";
        attribute :>> sourceSheet = "Interface";
        attribute :>> sourceRow = 91;
    }
    item trace_e30c550b4d4e8d52 : TraceRecord {
        attribute :>> elementId = "PORT::4239::高压隔离开关指令输出::ITM-CMD-017::输出";
        attribute :>> sourceFile = "Rail_MBSE_Function_Interface_v1_final.xlsx";
        attribute :>> sourceSheet = "Interface";
        attribute :>> sourceRow = 92;
    }
    item trace_30bf7d79603b941d : TraceRecord {
        attribute :>> elementId = "PORT::4239::高压隔离开关状态输入::ITM-STA-014::输入";
        attribute :>> sourceFile = "Rail_MBSE_Function_Interface_v1_final.xlsx";
        attribute :>> sourceSheet = "Interface";
        attribute :>> sourceRow = 93;
    }
    item trace_efc0e0ead5465ae4 : TraceRecord {
        attribute :>> elementId = "PORT::4241::低压控制电能端口::ITM-PHY-015::双向物理";
        attribute :>> sourceFile = "Rail_MBSE_Function_Interface_v1_final.xlsx";
        attribute :>> sourceSheet = "Interface";
        attribute :>> sourceRow = 94;
    }
    item trace_efaba262d19c325f : TraceRecord {
        attribute :>> elementId = "PORT::4241::回馈电网功率输出::ITM-ACC-003::输出";
        attribute :>> sourceFile = "Rail_MBSE_Function_Interface_v1_final.xlsx";
        attribute :>> sourceSheet = "Interface";
        attribute :>> sourceRow = 95;
    }
    item trace_14501c1527ffc885 : TraceRecord {
        attribute :>> elementId = "PORT::4241::回馈电网累计能量输出::ITM-ACC-009::输出";
        attribute :>> sourceFile = "Rail_MBSE_Function_Interface_v1_final.xlsx";
        attribute :>> sourceSheet = "Interface";
        attribute :>> sourceRow = 96;
    }
    item trace_c0f06cc787fcafcb : TraceRecord {
        attribute :>> elementId = "PORT::4241::牵引实际功率输出::ITM-ACC-001::输出";
        attribute :>> sourceFile = "Rail_MBSE_Function_Interface_v1_final.xlsx";
        attribute :>> sourceSheet = "Interface";
        attribute :>> sourceRow = 97;
    }
    item trace_110b5a4be355bd73 : TraceRecord {
        attribute :>> elementId = "PORT::4241::牵引累计能量输出::ITM-ACC-007::输出";
        attribute :>> sourceFile = "Rail_MBSE_Function_Interface_v1_final.xlsx";
        attribute :>> sourceSheet = "Interface";
        attribute :>> sourceRow = 98;
    }
    item trace_93eb42e9bb89d9ec : TraceRecord {
        attribute :>> elementId = "PORT::4241::能量计量有效状态输出::ITM-STA-035::输出";
        attribute :>> sourceFile = "Rail_MBSE_Function_Interface_v1_final.xlsx";
        attribute :>> sourceSheet = "Interface";
        attribute :>> sourceRow = 99;
    }
    item trace_2b7dd272027fdc0b : TraceRecord {
        attribute :>> elementId = "PORT::4241::高压线路电压输入::ITM-MEA-005::输入";
        attribute :>> sourceFile = "Rail_MBSE_Function_Interface_v1_final.xlsx";
        attribute :>> sourceSheet = "Interface";
        attribute :>> sourceRow = 100;
    }
    item trace_f81c0f4a108acec4 : TraceRecord {
        attribute :>> elementId = "PORT::4241::高压线路电流输入::ITM-MEA-006::输入";
        attribute :>> sourceFile = "Rail_MBSE_Function_Interface_v1_final.xlsx";
        attribute :>> sourceSheet = "Interface";
        attribute :>> sourceRow = 101;
    }
    item trace_45b0eaf9bb476ccf : TraceRecord {
        attribute :>> elementId = "PORT::4411::主回路侧回流电流端口::ITM-PHY-011::双向物理";
        attribute :>> sourceFile = "Rail_MBSE_Function_Interface_v1_final.xlsx";
        attribute :>> sourceSheet = "Interface";
        attribute :>> sourceRow = 102;
    }
    item trace_5e63cd1bffa78a41 : TraceRecord {
        attribute :>> elementId = "PORT::4411::回流侧电流端口::ITM-PHY-011::双向物理";
        attribute :>> sourceFile = "Rail_MBSE_Function_Interface_v1_final.xlsx";
        attribute :>> sourceSheet = "Interface";
        attribute :>> sourceRow = 103;
    }
    item trace_c61d1b462f69be85 : TraceRecord {
        attribute :>> elementId = "PORT::4411::热能_热流端口::ITM-PHY-013::双向物理";
        attribute :>> sourceFile = "Rail_MBSE_Function_Interface_v1_final.xlsx";
        attribute :>> sourceSheet = "Interface";
        attribute :>> sourceRow = 104;
    }
    item trace_e2c805a6993ee3dc : TraceRecord {
        attribute :>> elementId = "PORT::4412::主回路侧回流电流端口::ITM-PHY-011::双向物理";
        attribute :>> sourceFile = "Rail_MBSE_Function_Interface_v1_final.xlsx";
        attribute :>> sourceSheet = "Interface";
        attribute :>> sourceRow = 105;
    }
    item trace_f330d9bb72a522df : TraceRecord {
        attribute :>> elementId = "PORT::4412::回流侧电流端口::ITM-PHY-011::双向物理";
        attribute :>> sourceFile = "Rail_MBSE_Function_Interface_v1_final.xlsx";
        attribute :>> sourceSheet = "Interface";
        attribute :>> sourceRow = 106;
    }
    item trace_b031f017471c85ee : TraceRecord {
        attribute :>> elementId = "PORT::4412::热能_热流端口::ITM-PHY-013::双向物理";
        attribute :>> sourceFile = "Rail_MBSE_Function_Interface_v1_final.xlsx";
        attribute :>> sourceSheet = "Interface";
        attribute :>> sourceRow = 107;
    }
    item trace_cb582bd13ed15889 : TraceRecord {
        attribute :>> elementId = "PORT::4413::固定端回流电流端口::ITM-PHY-011::双向物理";
        attribute :>> sourceFile = "Rail_MBSE_Function_Interface_v1_final.xlsx";
        attribute :>> sourceSheet = "Interface";
        attribute :>> sourceRow = 108;
    }
    item trace_c808ea5883784df8 : TraceRecord {
        attribute :>> elementId = "PORT::4413::旋转端回流电流端口::ITM-PHY-011::双向物理";
        attribute :>> sourceFile = "Rail_MBSE_Function_Interface_v1_final.xlsx";
        attribute :>> sourceSheet = "Interface";
        attribute :>> sourceRow = 109;
    }
    item trace_a6f93ee77144741e : TraceRecord {
        attribute :>> elementId = "PORT::4511::牵引变压器次级交流电能端口::ITM-PHY-014::双向物理";
        attribute :>> sourceFile = "Rail_MBSE_Function_Interface_v1_final.xlsx";
        attribute :>> sourceSheet = "Interface";
        attribute :>> sourceRow = 110;
    }
    item trace_c782fb362436088e : TraceRecord {
        attribute :>> elementId = "PORT::4511::高压交流电能端口::ITM-PHY-001::双向物理";
        attribute :>> sourceFile = "Rail_MBSE_Function_Interface_v1_final.xlsx";
        attribute :>> sourceSheet = "Interface";
        attribute :>> sourceRow = 111;
    }
    item trace_88e2bd038f100aa3 : TraceRecord {
        attribute :>> elementId = "PORT::4513::第一交流电能端口::ITM-PHY-014::双向物理";
        attribute :>> sourceFile = "Rail_MBSE_Function_Interface_v1_final.xlsx";
        attribute :>> sourceSheet = "Interface";
        attribute :>> sourceRow = 112;
    }
    item trace_f597e9dc63931270 : TraceRecord {
        attribute :>> elementId = "PORT::4513::第二交流电能端口::ITM-PHY-014::双向物理";
        attribute :>> sourceFile = "Rail_MBSE_Function_Interface_v1_final.xlsx";
        attribute :>> sourceSheet = "Interface";
        attribute :>> sourceRow = 113;
    }
    item trace_b094956bc66dfaad : TraceRecord {
        attribute :>> elementId = "PORT::4517::主变压器温度输出::ITM-MEA-022::输出";
        attribute :>> sourceFile = "Rail_MBSE_Function_Interface_v1_final.xlsx";
        attribute :>> sourceSheet = "Interface";
        attribute :>> sourceRow = 114;
    }
    item trace_fa22ceafa52cda89 : TraceRecord {
        attribute :>> elementId = "PORT::4517::低压控制电能端口::ITM-PHY-015::双向物理";
        attribute :>> sourceFile = "Rail_MBSE_Function_Interface_v1_final.xlsx";
        attribute :>> sourceSheet = "Interface";
        attribute :>> sourceRow = 115;
    }
    item trace_b93b1716e8b4e844 : TraceRecord {
        attribute :>> elementId = "PORT::4517::高压系统故障状态输出::ITM-STA-016::输出";
        attribute :>> sourceFile = "Rail_MBSE_Function_Interface_v1_final.xlsx";
        attribute :>> sourceSheet = "Interface";
        attribute :>> sourceRow = 116;
    }
    item trace_f46b3d97e0fceb9e : TraceRecord {
        attribute :>> elementId = "PORT::4518::主变压器温度输入::ITM-MEA-022::输入";
        attribute :>> sourceFile = "Rail_MBSE_Function_Interface_v1_final.xlsx";
        attribute :>> sourceSheet = "Interface";
        attribute :>> sourceRow = 117;
    }
    item trace_950aee7777f5ea28 : TraceRecord {
        attribute :>> elementId = "PORT::4518::低压控制电能端口::ITM-PHY-015::双向物理";
        attribute :>> sourceFile = "Rail_MBSE_Function_Interface_v1_final.xlsx";
        attribute :>> sourceSheet = "Interface";
        attribute :>> sourceRow = 118;
    }
    item trace_c08bc1e5a0818e4a : TraceRecord {
        attribute :>> elementId = "PORT::4518::高压断路器指令输出::ITM-CMD-016::输出";
        attribute :>> sourceFile = "Rail_MBSE_Function_Interface_v1_final.xlsx";
        attribute :>> sourceSheet = "Interface";
        attribute :>> sourceRow = 119;
    }
    item trace_67eef246e016ac82 : TraceRecord {
        attribute :>> elementId = "PORT::4518::高压断路器状态输入::ITM-STA-013::输入";
        attribute :>> sourceFile = "Rail_MBSE_Function_Interface_v1_final.xlsx";
        attribute :>> sourceSheet = "Interface";
        attribute :>> sourceRow = 120;
    }
    item trace_a87c9390595138d6 : TraceRecord {
        attribute :>> elementId = "PORT::4518::高压系统故障状态输入::ITM-STA-016::输入";
        attribute :>> sourceFile = "Rail_MBSE_Function_Interface_v1_final.xlsx";
        attribute :>> sourceSheet = "Interface";
        attribute :>> sourceRow = 121;
    }
    item trace_a9ddcab662f35564 : TraceRecord {
        attribute :>> elementId = "PORT::5111::中间直流母线电压输入::ITM-MEA-008::输入";
        attribute :>> sourceFile = "Rail_MBSE_Function_Interface_v1_final.xlsx";
        attribute :>> sourceSheet = "Interface";
        attribute :>> sourceRow = 122;
    }
    item trace_0e00d1e837346b81 : TraceRecord {
        attribute :>> elementId = "PORT::5111::中间直流母线电流输入::ITM-MEA-009::输入";
        attribute :>> sourceFile = "Rail_MBSE_Function_Interface_v1_final.xlsx";
        attribute :>> sourceSheet = "Interface";
        attribute :>> sourceRow = 123;
    }
    item trace_9ceb0295e403e673 : TraceRecord {
        attribute :>> elementId = "PORT::5111::低压控制电能端口::ITM-PHY-015::双向物理";
        attribute :>> sourceFile = "Rail_MBSE_Function_Interface_v1_final.xlsx";
        attribute :>> sourceSheet = "Interface";
        attribute :>> sourceRow = 124;
    }
    item trace_6076ccac9d0762b3 : TraceRecord {
        attribute :>> elementId = "PORT::5111::再生功率上限输出::ITM-LIM-004::输出";
        attribute :>> sourceFile = "Rail_MBSE_Function_Interface_v1_final.xlsx";
        attribute :>> sourceSheet = "Interface";
        attribute :>> sourceRow = 125;
    }
    item trace_cd7720cf9a4eae22 : TraceRecord {
        attribute :>> elementId = "PORT::5111::接触网可接收功率输出::ITM-LIM-005::输出";
        attribute :>> sourceFile = "Rail_MBSE_Function_Interface_v1_final.xlsx";
        attribute :>> sourceSheet = "Interface";
        attribute :>> sourceRow = 126;
    }
    item trace_f5af02c6a1f2ad2c : TraceRecord {
        attribute :>> elementId = "PORT::5111::牵引变流器故障状态输出::ITM-STA-019::输出";
        attribute :>> sourceFile = "Rail_MBSE_Function_Interface_v1_final.xlsx";
        attribute :>> sourceSheet = "Interface";
        attribute :>> sourceRow = 127;
    }
    item trace_c8b770c2e6dd3117 : TraceRecord {
        attribute :>> elementId = "PORT::5111::线路频率输入::ITM-MEA-007::输入";
        attribute :>> sourceFile = "Rail_MBSE_Function_Interface_v1_final.xlsx";
        attribute :>> sourceSheet = "Interface";
        attribute :>> sourceRow = 128;
    }
    item trace_4963dcfde3fa1724 : TraceRecord {
        attribute :>> elementId = "PORT::5111::网侧变流器状态输出::ITM-STA-017::输出";
        attribute :>> sourceFile = "Rail_MBSE_Function_Interface_v1_final.xlsx";
        attribute :>> sourceSheet = "Interface";
        attribute :>> sourceRow = 129;
    }
    item trace_3c696476f82c2ae5 : TraceRecord {
        attribute :>> elementId = "PORT::5111::网侧变流控制指令输出::ITM-CMD-010::输出";
        attribute :>> sourceFile = "Rail_MBSE_Function_Interface_v1_final.xlsx";
        attribute :>> sourceSheet = "Interface";
        attribute :>> sourceRow = 130;
    }
    item trace_5f90d6dd8fba4321 : TraceRecord {
        attribute :>> elementId = "PORT::5111::高压线路电压输入::ITM-MEA-005::输入";
        attribute :>> sourceFile = "Rail_MBSE_Function_Interface_v1_final.xlsx";
        attribute :>> sourceSheet = "Interface";
        attribute :>> sourceRow = 131;
    }
    item trace_651700e69b7dccba : TraceRecord {
        attribute :>> elementId = "PORT::5111::高压线路电流输入::ITM-MEA-006::输入";
        attribute :>> sourceFile = "Rail_MBSE_Function_Interface_v1_final.xlsx";
        attribute :>> sourceSheet = "Interface";
        attribute :>> sourceRow = 132;
    }
    item trace_69252f780afe77e0 : TraceRecord {
        attribute :>> elementId = "PORT::5112::中间直流母线电压输入::ITM-MEA-008::输入";
        attribute :>> sourceFile = "Rail_MBSE_Function_Interface_v1_final.xlsx";
        attribute :>> sourceSheet = "Interface";
        attribute :>> sourceRow = 133;
    }
    item trace_6ad9df7ab3c91425 : TraceRecord {
        attribute :>> elementId = "PORT::5112::中间直流母线电流输入::ITM-MEA-009::输入";
        attribute :>> sourceFile = "Rail_MBSE_Function_Interface_v1_final.xlsx";
        attribute :>> sourceSheet = "Interface";
        attribute :>> sourceRow = 134;
    }
    item trace_c60f875ac7e265d0 : TraceRecord {
        attribute :>> elementId = "PORT::5112::低压控制电能端口::ITM-PHY-015::双向物理";
        attribute :>> sourceFile = "Rail_MBSE_Function_Interface_v1_final.xlsx";
        attribute :>> sourceSheet = "Interface";
        attribute :>> sourceRow = 135;
    }
    item trace_4bfdb59776ff813f : TraceRecord {
        attribute :>> elementId = "PORT::5112::再生功率上限输出::ITM-LIM-004::输出";
        attribute :>> sourceFile = "Rail_MBSE_Function_Interface_v1_final.xlsx";
        attribute :>> sourceSheet = "Interface";
        attribute :>> sourceRow = 136;
    }
    item trace_f2ec293da4f6084c : TraceRecord {
        attribute :>> elementId = "PORT::5112::动态制动可用状态输出::ITM-STA-002::输出";
        attribute :>> sourceFile = "Rail_MBSE_Function_Interface_v1_final.xlsx";
        attribute :>> sourceSheet = "Interface";
        attribute :>> sourceRow = 137;
    }
    item trace_b88bbe834e3c6412 : TraceRecord {
        attribute :>> elementId = "PORT::5112::可用动态制动力输出::ITM-LIM-001::输出";
        attribute :>> sourceFile = "Rail_MBSE_Function_Interface_v1_final.xlsx";
        attribute :>> sourceSheet = "Interface";
        attribute :>> sourceRow = 138;
    }
    item trace_13733b4e36d92f10 : TraceRecord {
        attribute :>> elementId = "PORT::5112::牵引_再生转矩上限输出::ITM-LIM-003::输出";
        attribute :>> sourceFile = "Rail_MBSE_Function_Interface_v1_final.xlsx";
        attribute :>> sourceSheet = "Interface";
        attribute :>> sourceRow = 139;
    }
    item trace_32a86e4500c85071 : TraceRecord {
        attribute :>> elementId = "PORT::5112::牵引变流器故障状态输出::ITM-STA-019::输出";
        attribute :>> sourceFile = "Rail_MBSE_Function_Interface_v1_final.xlsx";
        attribute :>> sourceSheet = "Interface";
        attribute :>> sourceRow = 140;
    }
    item trace_5337e32cd07bb034 : TraceRecord {
        attribute :>> elementId = "PORT::5112::牵引可用状态输出::ITM-STA-001::输出";
        attribute :>> sourceFile = "Rail_MBSE_Function_Interface_v1_final.xlsx";
        attribute :>> sourceSheet = "Interface";
        attribute :>> sourceRow = 141;
    }
    item trace_4557e9b0656c46f5 : TraceRecord {
        attribute :>> elementId = "PORT::5112::牵引电机实际转矩输入::ITM-MEA-012::输入";
        attribute :>> sourceFile = "Rail_MBSE_Function_Interface_v1_final.xlsx";
        attribute :>> sourceSheet = "Interface";
        attribute :>> sourceRow = 142;
    }
    item trace_6ce5fb5c81d47ab4 : TraceRecord {
        attribute :>> elementId = "PORT::5112::牵引电机转矩请求输入::ITM-CMD-012::输入";
        attribute :>> sourceFile = "Rail_MBSE_Function_Interface_v1_final.xlsx";
        attribute :>> sourceSheet = "Interface";
        attribute :>> sourceRow = 143;
    }
    item trace_780596fabcc73a0f : TraceRecord {
        attribute :>> elementId = "PORT::5112::牵引电机转速输入::ITM-MEA-004::输入";
        attribute :>> sourceFile = "Rail_MBSE_Function_Interface_v1_final.xlsx";
        attribute :>> sourceSheet = "Interface";
        attribute :>> sourceRow = 144;
    }
    item trace_f6a2c78620450314 : TraceRecord {
        attribute :>> elementId = "PORT::5112::电机侧变流器状态输出::ITM-STA-018::输出";
        attribute :>> sourceFile = "Rail_MBSE_Function_Interface_v1_final.xlsx";
        attribute :>> sourceSheet = "Interface";
        attribute :>> sourceRow = 145;
    }
    item trace_c98f6aa887541378 : TraceRecord {
        attribute :>> elementId = "PORT::5112::电机侧变流控制指令输出::ITM-CMD-011::输出";
        attribute :>> sourceFile = "Rail_MBSE_Function_Interface_v1_final.xlsx";
        attribute :>> sourceSheet = "Interface";
        attribute :>> sourceRow = 146;
    }
    item trace_21e86fb073b61523 : TraceRecord {
        attribute :>> elementId = "PORT::5112::电机侧相电压输入::ITM-MEA-011::输入";
        attribute :>> sourceFile = "Rail_MBSE_Function_Interface_v1_final.xlsx";
        attribute :>> sourceSheet = "Interface";
        attribute :>> sourceRow = 147;
    }
    item trace_3db204c2f5a83c7f : TraceRecord {
        attribute :>> elementId = "PORT::5112::电机侧相电流输入::ITM-MEA-010::输入";
        attribute :>> sourceFile = "Rail_MBSE_Function_Interface_v1_final.xlsx";
        attribute :>> sourceSheet = "Interface";
        attribute :>> sourceRow = 148;
    }
    item trace_2af3dfa3c81ea109 : TraceRecord {
        attribute :>> elementId = "PORT::5113::中间直流母线电压输出::ITM-MEA-008::输出";
        attribute :>> sourceFile = "Rail_MBSE_Function_Interface_v1_final.xlsx";
        attribute :>> sourceSheet = "Interface";
        attribute :>> sourceRow = 149;
    }
    item trace_4e1f60c0e22c417d : TraceRecord {
        attribute :>> elementId = "PORT::5113::中间直流母线电流输出::ITM-MEA-009::输出";
        attribute :>> sourceFile = "Rail_MBSE_Function_Interface_v1_final.xlsx";
        attribute :>> sourceSheet = "Interface";
        attribute :>> sourceRow = 150;
    }
    item trace_7668c7c1973850f4 : TraceRecord {
        attribute :>> elementId = "PORT::5113::中间直流环节保护状态输出::ITM-STA-020::输出";
        attribute :>> sourceFile = "Rail_MBSE_Function_Interface_v1_final.xlsx";
        attribute :>> sourceSheet = "Interface";
        attribute :>> sourceRow = 151;
    }
    item trace_6f5e3f6e1f0f9b1a : TraceRecord {
        attribute :>> elementId = "PORT::5113::低压控制电能端口::ITM-PHY-015::双向物理";
        attribute :>> sourceFile = "Rail_MBSE_Function_Interface_v1_final.xlsx";
        attribute :>> sourceSheet = "Interface";
        attribute :>> sourceRow = 152;
    }
    item trace_d93ff3dea2be11bd : TraceRecord {
        attribute :>> elementId = "PORT::5113::牵引变流器故障状态输出::ITM-STA-019::输出";
        attribute :>> sourceFile = "Rail_MBSE_Function_Interface_v1_final.xlsx";
        attribute :>> sourceSheet = "Interface";
        attribute :>> sourceRow = 153;
    }
    item trace_a16fb7ddd6338cf7 : TraceRecord {
        attribute :>> elementId = "PORT::5113::牵引变流器温度输出::ITM-MEA-023::输出";
        attribute :>> sourceFile = "Rail_MBSE_Function_Interface_v1_final.xlsx";
        attribute :>> sourceSheet = "Interface";
        attribute :>> sourceRow = 154;
    }
    item trace_4be030fa7e242206 : TraceRecord {
        attribute :>> elementId = "PORT::5113::电机侧相电流输出::ITM-MEA-010::输出";
        attribute :>> sourceFile = "Rail_MBSE_Function_Interface_v1_final.xlsx";
        attribute :>> sourceSheet = "Interface";
        attribute :>> sourceRow = 155;
    }
    item trace_d8b59663e8e8813a : TraceRecord {
        attribute :>> elementId = "PORT::5113::直流母线电压上限输出::ITM-LIM-007::输出";
        attribute :>> sourceFile = "Rail_MBSE_Function_Interface_v1_final.xlsx";
        attribute :>> sourceSheet = "Interface";
        attribute :>> sourceRow = 156;
    }
    item trace_e5b052bb75ba8a31 : TraceRecord {
        attribute :>> elementId = "PORT::5121::中间直流电能端口::ITM-PHY-003::双向物理";
        attribute :>> sourceFile = "Rail_MBSE_Function_Interface_v1_final.xlsx";
        attribute :>> sourceSheet = "Interface";
        attribute :>> sourceRow = 157;
    }
    item trace_9dedfe88c8a34261 : TraceRecord {
        attribute :>> elementId = "PORT::5121::牵引变压器次级交流电能端口::ITM-PHY-014::双向物理";
        attribute :>> sourceFile = "Rail_MBSE_Function_Interface_v1_final.xlsx";
        attribute :>> sourceSheet = "Interface";
        attribute :>> sourceRow = 158;
    }
    item trace_809fd610416051c1 : TraceRecord {
        attribute :>> elementId = "PORT::5121::直流牵引供电电能端口::ITM-PHY-002::双向物理";
        attribute :>> sourceFile = "Rail_MBSE_Function_Interface_v1_final.xlsx";
        attribute :>> sourceSheet = "Interface";
        attribute :>> sourceRow = 159;
    }
    item trace_56d2d83f54b98301 : TraceRecord {
        attribute :>> elementId = "PORT::5121::预充电指令输入::ITM-CMD-013::输入";
        attribute :>> sourceFile = "Rail_MBSE_Function_Interface_v1_final.xlsx";
        attribute :>> sourceSheet = "Interface";
        attribute :>> sourceRow = 160;
    }
    item trace_923b8f78dd634c21 : TraceRecord {
        attribute :>> elementId = "PORT::5121::预充电状态输出::ITM-STA-021::输出";
        attribute :>> sourceFile = "Rail_MBSE_Function_Interface_v1_final.xlsx";
        attribute :>> sourceSheet = "Interface";
        attribute :>> sourceRow = 161;
    }
    item trace_6e156eb66bd95a75 : TraceRecord {
        attribute :>> elementId = "PORT::5122::中间直流电能端口::ITM-PHY-003::双向物理";
        attribute :>> sourceFile = "Rail_MBSE_Function_Interface_v1_final.xlsx";
        attribute :>> sourceSheet = "Interface";
        attribute :>> sourceRow = 162;
    }
    item trace_0b57347688ba1240 : TraceRecord {
        attribute :>> elementId = "PORT::5122::牵引变压器次级交流电能端口::ITM-PHY-014::双向物理";
        attribute :>> sourceFile = "Rail_MBSE_Function_Interface_v1_final.xlsx";
        attribute :>> sourceSheet = "Interface";
        attribute :>> sourceRow = 163;
    }
    item trace_32a63d8c830a3ed0 : TraceRecord {
        attribute :>> elementId = "PORT::5122::牵引输入接通指令输入::ITM-CMD-014::输入";
        attribute :>> sourceFile = "Rail_MBSE_Function_Interface_v1_final.xlsx";
        attribute :>> sourceSheet = "Interface";
        attribute :>> sourceRow = 164;
    }
    item trace_a512199cf2d52036 : TraceRecord {
        attribute :>> elementId = "PORT::5122::牵引输入接通状态输出::ITM-STA-022::输出";
        attribute :>> sourceFile = "Rail_MBSE_Function_Interface_v1_final.xlsx";
        attribute :>> sourceSheet = "Interface";
        attribute :>> sourceRow = 165;
    }
    item trace_08aeac9ca9c693f3 : TraceRecord {
        attribute :>> elementId = "PORT::5122::直流牵引供电电能端口::ITM-PHY-002::双向物理";
        attribute :>> sourceFile = "Rail_MBSE_Function_Interface_v1_final.xlsx";
        attribute :>> sourceSheet = "Interface";
        attribute :>> sourceRow = 166;
    }
    item trace_58be8015ffe61769 : TraceRecord {
        attribute :>> elementId = "PORT::5131::中间直流母线电压输出::ITM-MEA-008::输出";
        attribute :>> sourceFile = "Rail_MBSE_Function_Interface_v1_final.xlsx";
        attribute :>> sourceSheet = "Interface";
        attribute :>> sourceRow = 167;
    }
    item trace_0772d9885daa45bb : TraceRecord {
        attribute :>> elementId = "PORT::5131::中间直流母线电流输出::ITM-MEA-009::输出";
        attribute :>> sourceFile = "Rail_MBSE_Function_Interface_v1_final.xlsx";
        attribute :>> sourceSheet = "Interface";
        attribute :>> sourceRow = 168;
    }
    item trace_f010ea68f7dddd01 : TraceRecord {
        attribute :>> elementId = "PORT::5131::中间直流电能端口::ITM-PHY-003::双向物理";
        attribute :>> sourceFile = "Rail_MBSE_Function_Interface_v1_final.xlsx";
        attribute :>> sourceSheet = "Interface";
        attribute :>> sourceRow = 169;
    }
    item trace_95979f7c6bb276e7 : TraceRecord {
        attribute :>> elementId = "PORT::5131::回馈电网功率输出::ITM-ACC-003::输出";
        attribute :>> sourceFile = "Rail_MBSE_Function_Interface_v1_final.xlsx";
        attribute :>> sourceSheet = "Interface";
        attribute :>> sourceRow = 170;
    }
    item trace_32d77ca0c1d88b50 : TraceRecord {
        attribute :>> elementId = "PORT::5131::牵引变压器次级交流电能端口::ITM-PHY-014::双向物理";
        attribute :>> sourceFile = "Rail_MBSE_Function_Interface_v1_final.xlsx";
        attribute :>> sourceSheet = "Interface";
        attribute :>> sourceRow = 171;
    }
    item trace_c06b535bf90fa905 : TraceRecord {
        attribute :>> elementId = "PORT::5131::网侧变流控制指令输入::ITM-CMD-010::输入";
        attribute :>> sourceFile = "Rail_MBSE_Function_Interface_v1_final.xlsx";
        attribute :>> sourceSheet = "Interface";
        attribute :>> sourceRow = 172;
    }
    item trace_3b17660257f9fac5 : TraceRecord {
        attribute :>> elementId = "PORT::5131::高压线路电压输出::ITM-MEA-005::输出";
        attribute :>> sourceFile = "Rail_MBSE_Function_Interface_v1_final.xlsx";
        attribute :>> sourceSheet = "Interface";
        attribute :>> sourceRow = 173;
    }
    item trace_5e454de063d535e5 : TraceRecord {
        attribute :>> elementId = "PORT::5131::高压线路电流输出::ITM-MEA-006::输出";
        attribute :>> sourceFile = "Rail_MBSE_Function_Interface_v1_final.xlsx";
        attribute :>> sourceSheet = "Interface";
        attribute :>> sourceRow = 174;
    }
    item trace_770f7e1c507cc073 : TraceRecord {
        attribute :>> elementId = "PORT::5132::三相交流电能端口::ITM-PHY-004::双向物理";
        attribute :>> sourceFile = "Rail_MBSE_Function_Interface_v1_final.xlsx";
        attribute :>> sourceSheet = "Interface";
        attribute :>> sourceRow = 175;
    }
    item trace_4fd822f2b574e9e6 : TraceRecord {
        attribute :>> elementId = "PORT::5132::中间直流母线电压输出::ITM-MEA-008::输出";
        attribute :>> sourceFile = "Rail_MBSE_Function_Interface_v1_final.xlsx";
        attribute :>> sourceSheet = "Interface";
        attribute :>> sourceRow = 176;
    }
    item trace_097124295bc446b2 : TraceRecord {
        attribute :>> elementId = "PORT::5132::中间直流母线电流输出::ITM-MEA-009::输出";
        attribute :>> sourceFile = "Rail_MBSE_Function_Interface_v1_final.xlsx";
        attribute :>> sourceSheet = "Interface";
        attribute :>> sourceRow = 177;
    }
    item trace_e9be022214796a74 : TraceRecord {
        attribute :>> elementId = "PORT::5132::中间直流电能端口::ITM-PHY-003::双向物理";
        attribute :>> sourceFile = "Rail_MBSE_Function_Interface_v1_final.xlsx";
        attribute :>> sourceSheet = "Interface";
        attribute :>> sourceRow = 178;
    }
    item trace_75d86c9dc39b94b8 : TraceRecord {
        attribute :>> elementId = "PORT::5132::实际再生功率输出::ITM-ACC-002::输出";
        attribute :>> sourceFile = "Rail_MBSE_Function_Interface_v1_final.xlsx";
        attribute :>> sourceSheet = "Interface";
        attribute :>> sourceRow = 179;
    }
    item trace_406d292901368d53 : TraceRecord {
        attribute :>> elementId = "PORT::5132::电机侧变流控制指令输入::ITM-CMD-011::输入";
        attribute :>> sourceFile = "Rail_MBSE_Function_Interface_v1_final.xlsx";
        attribute :>> sourceSheet = "Interface";
        attribute :>> sourceRow = 180;
    }
    item trace_22f4369ba0161f6e : TraceRecord {
        attribute :>> elementId = "PORT::5132::电机侧相电压输出::ITM-MEA-011::输出";
        attribute :>> sourceFile = "Rail_MBSE_Function_Interface_v1_final.xlsx";
        attribute :>> sourceSheet = "Interface";
        attribute :>> sourceRow = 181;
    }
    item trace_7044b6667673db95 : TraceRecord {
        attribute :>> elementId = "PORT::5132::电机侧相电流输出::ITM-MEA-010::输出";
        attribute :>> sourceFile = "Rail_MBSE_Function_Interface_v1_final.xlsx";
        attribute :>> sourceSheet = "Interface";
        attribute :>> sourceRow = 182;
    }
    item trace_60d9996fadd55bff : TraceRecord {
        attribute :>> elementId = "PORT::5133::中间直流母线电压输入::ITM-MEA-008::输入";
        attribute :>> sourceFile = "Rail_MBSE_Function_Interface_v1_final.xlsx";
        attribute :>> sourceSheet = "Interface";
        attribute :>> sourceRow = 183;
    }
    item trace_b97ef71e558464ef : TraceRecord {
        attribute :>> elementId = "PORT::5133::低压控制电能端口::ITM-PHY-015::双向物理";
        attribute :>> sourceFile = "Rail_MBSE_Function_Interface_v1_final.xlsx";
        attribute :>> sourceSheet = "Interface";
        attribute :>> sourceRow = 184;
    }
    item trace_77ee52e55ac1ca4e : TraceRecord {
        attribute :>> elementId = "PORT::5133::制动斩波器指令输入::ITM-CMD-015::输入";
        attribute :>> sourceFile = "Rail_MBSE_Function_Interface_v1_final.xlsx";
        attribute :>> sourceSheet = "Interface";
        attribute :>> sourceRow = 185;
    }
    item trace_ceecb00c1539e058 : TraceRecord {
        attribute :>> elementId = "PORT::5133::制动斩波器状态输出::ITM-STA-023::输出";
        attribute :>> sourceFile = "Rail_MBSE_Function_Interface_v1_final.xlsx";
        attribute :>> sourceSheet = "Interface";
        attribute :>> sourceRow = 186;
    }
    item trace_cb7199d5a5b150b9 : TraceRecord {
        attribute :>> elementId = "PORT::5133::制动电阻可耗散功率输出::ITM-LIM-006::输出";
        attribute :>> sourceFile = "Rail_MBSE_Function_Interface_v1_final.xlsx";
        attribute :>> sourceSheet = "Interface";
        attribute :>> sourceRow = 187;
    }
    item trace_14fbc389883862a8 : TraceRecord {
        attribute :>> elementId = "PORT::5142::中间直流电能端口::ITM-PHY-003::双向物理";
        attribute :>> sourceFile = "Rail_MBSE_Function_Interface_v1_final.xlsx";
        attribute :>> sourceSheet = "Interface";
        attribute :>> sourceRow = 188;
    }
    item trace_2057e03c844b131c : TraceRecord {
        attribute :>> elementId = "PORT::5142::制动电阻温度输出::ITM-MEA-024::输出";
        attribute :>> sourceFile = "Rail_MBSE_Function_Interface_v1_final.xlsx";
        attribute :>> sourceSheet = "Interface";
        attribute :>> sourceRow = 189;
    }
    item trace_ff09931c451e831b : TraceRecord {
        attribute :>> elementId = "PORT::5142::制动电阻耗散功率输出::ITM-ACC-005::输出";
        attribute :>> sourceFile = "Rail_MBSE_Function_Interface_v1_final.xlsx";
        attribute :>> sourceSheet = "Interface";
        attribute :>> sourceRow = 190;
    }
    item trace_876f0faee3baf027 : TraceRecord {
        attribute :>> elementId = "PORT::5142::制动电阻耗散累计能量输出::ITM-ACC-012::输出";
        attribute :>> sourceFile = "Rail_MBSE_Function_Interface_v1_final.xlsx";
        attribute :>> sourceSheet = "Interface";
        attribute :>> sourceRow = 191;
    }
    item trace_7c7ad9996d24b706 : TraceRecord {
        attribute :>> elementId = "PORT::5142::热能_热流端口::ITM-PHY-013::双向物理";
        attribute :>> sourceFile = "Rail_MBSE_Function_Interface_v1_final.xlsx";
        attribute :>> sourceSheet = "Interface";
        attribute :>> sourceRow = 192;
    }
    item trace_1680714c67f7d311 : TraceRecord {
        attribute :>> elementId = "PORT::5145::中间直流母线电压输出::ITM-MEA-008::输出";
        attribute :>> sourceFile = "Rail_MBSE_Function_Interface_v1_final.xlsx";
        attribute :>> sourceSheet = "Interface";
        attribute :>> sourceRow = 193;
    }
    item trace_a9cc4822e30a5ede : TraceRecord {
        attribute :>> elementId = "PORT::5145::中间直流母线电流输出::ITM-MEA-009::输出";
        attribute :>> sourceFile = "Rail_MBSE_Function_Interface_v1_final.xlsx";
        attribute :>> sourceSheet = "Interface";
        attribute :>> sourceRow = 194;
    }
    item trace_0fe575c7a29bac8c : TraceRecord {
        attribute :>> elementId = "PORT::5145::中间直流环节保护状态输出::ITM-STA-020::输出";
        attribute :>> sourceFile = "Rail_MBSE_Function_Interface_v1_final.xlsx";
        attribute :>> sourceSheet = "Interface";
        attribute :>> sourceRow = 195;
    }
    item trace_b22756bb5d4e9b69 : TraceRecord {
        attribute :>> elementId = "PORT::5145::低压控制电能端口::ITM-PHY-015::双向物理";
        attribute :>> sourceFile = "Rail_MBSE_Function_Interface_v1_final.xlsx";
        attribute :>> sourceSheet = "Interface";
        attribute :>> sourceRow = 196;
    }
    item trace_e58f80e07056f3fb : TraceRecord {
        attribute :>> elementId = "PORT::5145::制动斩波器指令输出::ITM-CMD-015::输出";
        attribute :>> sourceFile = "Rail_MBSE_Function_Interface_v1_final.xlsx";
        attribute :>> sourceSheet = "Interface";
        attribute :>> sourceRow = 197;
    }
    item trace_3c3f036735b04fe0 : TraceRecord {
        attribute :>> elementId = "PORT::5145::直流母线电压上限输出::ITM-LIM-007::输出";
        attribute :>> sourceFile = "Rail_MBSE_Function_Interface_v1_final.xlsx";
        attribute :>> sourceSheet = "Interface";
        attribute :>> sourceRow = 198;
    }
    item trace_57f3c317ac0c860d : TraceRecord {
        attribute :>> elementId = "PORT::5311::三相交流电能端口::ITM-PHY-004::双向物理";
        attribute :>> sourceFile = "Rail_MBSE_Function_Interface_v1_final.xlsx";
        attribute :>> sourceSheet = "Interface";
        attribute :>> sourceRow = 199;
    }
    item trace_97eb613c06ae1b2e : TraceRecord {
        attribute :>> elementId = "PORT::5311::旋转机械能端口::ITM-PHY-005::双向物理";
        attribute :>> sourceFile = "Rail_MBSE_Function_Interface_v1_final.xlsx";
        attribute :>> sourceSheet = "Interface";
        attribute :>> sourceRow = 200;
    }
    item trace_10bb4c4f0063bc18 : TraceRecord {
        attribute :>> elementId = "PORT::5311::牵引电机实际转矩输出::ITM-MEA-012::输出";
        attribute :>> sourceFile = "Rail_MBSE_Function_Interface_v1_final.xlsx";
        attribute :>> sourceSheet = "Interface";
        attribute :>> sourceRow = 201;
    }
    item trace_79c695a1342df24f : TraceRecord {
        attribute :>> elementId = "PORT::5311::牵引电机转速输出::ITM-MEA-004::输出";
        attribute :>> sourceFile = "Rail_MBSE_Function_Interface_v1_final.xlsx";
        attribute :>> sourceSheet = "Interface";
        attribute :>> sourceRow = 202;
    }
    item trace_537e9856bafa2a02 : TraceRecord {
        attribute :>> elementId = "PORT::5311::电机侧相电压输出::ITM-MEA-011::输出";
        attribute :>> sourceFile = "Rail_MBSE_Function_Interface_v1_final.xlsx";
        attribute :>> sourceSheet = "Interface";
        attribute :>> sourceRow = 203;
    }
    item trace_147751bb1b62d40a : TraceRecord {
        attribute :>> elementId = "PORT::5311::电机侧相电流输出::ITM-MEA-010::输出";
        attribute :>> sourceFile = "Rail_MBSE_Function_Interface_v1_final.xlsx";
        attribute :>> sourceSheet = "Interface";
        attribute :>> sourceRow = 204;
    }
    item trace_732b5a3acb4e2be0 : TraceRecord {
        attribute :>> elementId = "PORT::7124::主风压缩空气端口::ITM-PHY-008::双向物理";
        attribute :>> sourceFile = "Rail_MBSE_Function_Interface_v1_final.xlsx";
        attribute :>> sourceSheet = "Interface";
        attribute :>> sourceRow = 205;
    }
    item trace_d2f380834008b7d7 : TraceRecord {
        attribute :>> elementId = "PORT::7124::制动风缸压力输出::ITM-MEA-015::输出";
        attribute :>> sourceFile = "Rail_MBSE_Function_Interface_v1_final.xlsx";
        attribute :>> sourceSheet = "Interface";
        attribute :>> sourceRow = 206;
    }
    item trace_e275cbf47ef42c02 : TraceRecord {
        attribute :>> elementId = "PORT::7131::总风管末端压缩空气端口::ITM-PHY-008::双向物理";
        attribute :>> sourceFile = "Rail_MBSE_Function_Interface_v1_final.xlsx";
        attribute :>> sourceSheet = "Interface";
        attribute :>> sourceRow = 207;
    }
    item trace_e73ffca5021e0883 : TraceRecord {
        attribute :>> elementId = "PORT::7131::总风管首端压缩空气端口::ITM-PHY-008::双向物理";
        attribute :>> sourceFile = "Rail_MBSE_Function_Interface_v1_final.xlsx";
        attribute :>> sourceSheet = "Interface";
        attribute :>> sourceRow = 208;
    }
    item trace_b1c762907b90d07b : TraceRecord {
        attribute :>> elementId = "PORT::7142::主风压缩空气端口::ITM-PHY-008::双向物理";
        attribute :>> sourceFile = "Rail_MBSE_Function_Interface_v1_final.xlsx";
        attribute :>> sourceSheet = "Interface";
        attribute :>> sourceRow = 209;
    }
    item trace_3909c089bc66e61b : TraceRecord {
        attribute :>> elementId = "PORT::7142::低风压状态输出::ITM-STA-009::输出";
        attribute :>> sourceFile = "Rail_MBSE_Function_Interface_v1_final.xlsx";
        attribute :>> sourceSheet = "Interface";
        attribute :>> sourceRow = 210;
    }
    item trace_52f3b82b80918b84 : TraceRecord {
        attribute :>> elementId = "PORT::7142::总风管压力输出::ITM-MEA-014::输出";
        attribute :>> sourceFile = "Rail_MBSE_Function_Interface_v1_final.xlsx";
        attribute :>> sourceSheet = "Interface";
        attribute :>> sourceRow = 211;
    }
    item trace_b34d5a11f0a32260 : TraceRecord {
        attribute :>> elementId = "PORT::7211::低压控制电能端口::ITM-PHY-015::双向物理";
        attribute :>> sourceFile = "Rail_MBSE_Function_Interface_v1_final.xlsx";
        attribute :>> sourceSheet = "Interface";
        attribute :>> sourceRow = 212;
    }
    item trace_19f11c6ee3cbf055 : TraceRecord {
        attribute :>> elementId = "PORT::7211::低风压状态输入::ITM-STA-009::输入";
        attribute :>> sourceFile = "Rail_MBSE_Function_Interface_v1_final.xlsx";
        attribute :>> sourceSheet = "Interface";
        attribute :>> sourceRow = 213;
    }
    item trace_dc452be8b7368516 : TraceRecord {
        attribute :>> elementId = "PORT::7211::列车质量输入::ITM-MEA-018::输入";
        attribute :>> sourceFile = "Rail_MBSE_Function_Interface_v1_final.xlsx";
        attribute :>> sourceSheet = "Interface";
        attribute :>> sourceRow = 214;
    }
    item trace_e64f014311f04d50 : TraceRecord {
        attribute :>> elementId = "PORT::7211::列车速度输入::ITM-MEA-001::输入";
        attribute :>> sourceFile = "Rail_MBSE_Function_Interface_v1_final.xlsx";
        attribute :>> sourceSheet = "Interface";
        attribute :>> sourceRow = 215;
    }
    item trace_daaf414c1711f2bd : TraceRecord {
        attribute :>> elementId = "PORT::7211::制动安全回路状态输入::ITM-STA-025::输入";
        attribute :>> sourceFile = "Rail_MBSE_Function_Interface_v1_final.xlsx";
        attribute :>> sourceSheet = "Interface";
        attribute :>> sourceRow = 216;
    }
    item trace_ab6bd1b4df7dcdff : TraceRecord {
        attribute :>> elementId = "PORT::7211::制动拖滞状态输出::ITM-STA-008::输出";
        attribute :>> sourceFile = "Rail_MBSE_Function_Interface_v1_final.xlsx";
        attribute :>> sourceSheet = "Interface";
        attribute :>> sourceRow = 217;
    }
    item trace_0209c7a801f78e7e : TraceRecord {
        attribute :>> elementId = "PORT::7211::制动控制接触器指令输出::ITM-CMD-031::输出";
        attribute :>> sourceFile = "Rail_MBSE_Function_Interface_v1_final.xlsx";
        attribute :>> sourceSheet = "Interface";
        attribute :>> sourceRow = 218;
    }
    item trace_15b87d372ae097d8 : TraceRecord {
        attribute :>> elementId = "PORT::7211::制动控制故障状态输出::ITM-STA-007::输出";
        attribute :>> sourceFile = "Rail_MBSE_Function_Interface_v1_final.xlsx";
        attribute :>> sourceSheet = "Interface";
        attribute :>> sourceRow = 219;
    }
    item trace_77f0053899ab19da : TraceRecord {
        attribute :>> elementId = "PORT::7211::制动施加状态输出::ITM-STA-004::输出";
        attribute :>> sourceFile = "Rail_MBSE_Function_Interface_v1_final.xlsx";
        attribute :>> sourceSheet = "Interface";
        attribute :>> sourceRow = 220;
    }
    item trace_c4074d88ed5949ec : TraceRecord {
        attribute :>> elementId = "PORT::7211::制动电磁阀指令输出::ITM-CMD-022::输出";
        attribute :>> sourceFile = "Rail_MBSE_Function_Interface_v1_final.xlsx";
        attribute :>> sourceSheet = "Interface";
        attribute :>> sourceRow = 221;
    }
    item trace_c021f63639408eff : TraceRecord {
        attribute :>> elementId = "PORT::7211::制动系统可用状态输出::ITM-STA-003::输出";
        attribute :>> sourceFile = "Rail_MBSE_Function_Interface_v1_final.xlsx";
        attribute :>> sourceSheet = "Interface";
        attribute :>> sourceRow = 222;
    }
    item trace_abc190a288d4c9d5 : TraceRecord {
        attribute :>> elementId = "PORT::7211::制动缓解指令输出::ITM-CMD-019::输出";
        attribute :>> sourceFile = "Rail_MBSE_Function_Interface_v1_final.xlsx";
        attribute :>> sourceSheet = "Interface";
        attribute :>> sourceRow = 223;
    }
    item trace_ef5148faa6dc1c65 : TraceRecord {
        attribute :>> elementId = "PORT::7211::制动缓解状态输出::ITM-STA-005::输出";
        attribute :>> sourceFile = "Rail_MBSE_Function_Interface_v1_final.xlsx";
        attribute :>> sourceSheet = "Interface";
        attribute :>> sourceRow = 224;
    }
    item trace_f786158194c89c8a : TraceRecord {
        attribute :>> elementId = "PORT::7211::制动缸压力输入::ITM-MEA-016::输入";
        attribute :>> sourceFile = "Rail_MBSE_Function_Interface_v1_final.xlsx";
        attribute :>> sourceSheet = "Interface";
        attribute :>> sourceRow = 225;
    }
    item trace_a882b33038ce4623 : TraceRecord {
        attribute :>> elementId = "PORT::7211::制动隔离指令输出::ITM-CMD-020::输出";
        attribute :>> sourceFile = "Rail_MBSE_Function_Interface_v1_final.xlsx";
        attribute :>> sourceSheet = "Interface";
        attribute :>> sourceRow = 226;
    }
    item trace_43e35aa64c833efc : TraceRecord {
        attribute :>> elementId = "PORT::7211::制动隔离状态输出::ITM-STA-006::输出";
        attribute :>> sourceFile = "Rail_MBSE_Function_Interface_v1_final.xlsx";
        attribute :>> sourceSheet = "Interface";
        attribute :>> sourceRow = 227;
    }
    item trace_0194ebfed505dfb5 : TraceRecord {
        attribute :>> elementId = "PORT::7211::动态制动力请求输出::ITM-CMD-006::输出";
        attribute :>> sourceFile = "Rail_MBSE_Function_Interface_v1_final.xlsx";
        attribute :>> sourceSheet = "Interface";
        attribute :>> sourceRow = 228;
    }
    item trace_d26568a796272d7a : TraceRecord {
        attribute :>> elementId = "PORT::7211::动态制动可用状态输入::ITM-STA-002::输入";
        attribute :>> sourceFile = "Rail_MBSE_Function_Interface_v1_final.xlsx";
        attribute :>> sourceSheet = "Interface";
        attribute :>> sourceRow = 229;
    }
    item trace_e4d6047a07b1416e : TraceRecord {
        attribute :>> elementId = "PORT::7211::可用动态制动力输入::ITM-LIM-001::输入";
        attribute :>> sourceFile = "Rail_MBSE_Function_Interface_v1_final.xlsx";
        attribute :>> sourceSheet = "Interface";
        attribute :>> sourceRow = 230;
    }
    item trace_3e14ce961c10da8c : TraceRecord {
        attribute :>> elementId = "PORT::7211::可用摩擦制动力输出::ITM-LIM-002::输出";
        attribute :>> sourceFile = "Rail_MBSE_Function_Interface_v1_final.xlsx";
        attribute :>> sourceSheet = "Interface";
        attribute :>> sourceRow = 231;
    }
    item trace_fbdca500826ff2e8 : TraceRecord {
        attribute :>> elementId = "PORT::7211::可用黏着系数估计输入::ITM-MEA-021::输入";
        attribute :>> sourceFile = "Rail_MBSE_Function_Interface_v1_final.xlsx";
        attribute :>> sourceSheet = "Interface";
        attribute :>> sourceRow = 232;
    }
    item trace_5fc26e41f5b877b0 : TraceRecord {
        attribute :>> elementId = "PORT::7211::可用黏着限制输入::ITM-LIM-008::输入";
        attribute :>> sourceFile = "Rail_MBSE_Function_Interface_v1_final.xlsx";
        attribute :>> sourceSheet = "Interface";
        attribute :>> sourceRow = 233;
    }
    item trace_da3049ae66223d22 : TraceRecord {
        attribute :>> elementId = "PORT::7211::安全停车_制动请求输入::ITM-CMD-030::输入";
        attribute :>> sourceFile = "Rail_MBSE_Function_Interface_v1_final.xlsx";
        attribute :>> sourceSheet = "Interface";
        attribute :>> sourceRow = 234;
    }
    item trace_179bcc3fb8dacbbf : TraceRecord {
        attribute :>> elementId = "PORT::7211::实际动态制动力输入::ITM-MEA-013::输入";
        attribute :>> sourceFile = "Rail_MBSE_Function_Interface_v1_final.xlsx";
        attribute :>> sourceSheet = "Interface";
        attribute :>> sourceRow = 235;
    }
    item trace_5b7be52aa5b6e9d0 : TraceRecord {
        attribute :>> elementId = "PORT::7211::实际摩擦制动力输入::ITM-MEA-017::输入";
        attribute :>> sourceFile = "Rail_MBSE_Function_Interface_v1_final.xlsx";
        attribute :>> sourceSheet = "Interface";
        attribute :>> sourceRow = 236;
    }
    item trace_04cfaf63bfa3ed70 : TraceRecord {
        attribute :>> elementId = "PORT::7211::总风管压力输入::ITM-MEA-014::输入";
        attribute :>> sourceFile = "Rail_MBSE_Function_Interface_v1_final.xlsx";
        attribute :>> sourceSheet = "Interface";
        attribute :>> sourceRow = 237;
    }
    item trace_45bcc846bb19f806 : TraceRecord {
        attribute :>> elementId = "PORT::7211::摩擦制动力请求输出::ITM-CMD-007::输出";
        attribute :>> sourceFile = "Rail_MBSE_Function_Interface_v1_final.xlsx";
        attribute :>> sourceSheet = "Interface";
        attribute :>> sourceRow = 238;
    }
    item trace_a477083b284f478e : TraceRecord {
        attribute :>> elementId = "PORT::7211::最大允许减速度输入::ITM-LIM-014::输入";
        attribute :>> sourceFile = "Rail_MBSE_Function_Interface_v1_final.xlsx";
        attribute :>> sourceSheet = "Interface";
        attribute :>> sourceRow = 239;
    }
    item trace_8f4a8ea2188f4411 : TraceRecord {
        attribute :>> elementId = "PORT::7211::最大允许制动力输入::ITM-LIM-013::输入";
        attribute :>> sourceFile = "Rail_MBSE_Function_Interface_v1_final.xlsx";
        attribute :>> sourceSheet = "Interface";
        attribute :>> sourceRow = 240;
    }
    item trace_77afbfa330bfb95e : TraceRecord {
        attribute :>> elementId = "PORT::7211::服务制动请求输入::ITM-CMD-003::输入";
        attribute :>> sourceFile = "Rail_MBSE_Function_Interface_v1_final.xlsx";
        attribute :>> sourceSheet = "Interface";
        attribute :>> sourceRow = 241;
    }
    item trace_a53270fc181cff7c : TraceRecord {
        attribute :>> elementId = "PORT::7211::牵引切除请求输出::ITM-CMD-008::输出";
        attribute :>> sourceFile = "Rail_MBSE_Function_Interface_v1_final.xlsx";
        attribute :>> sourceSheet = "Interface";
        attribute :>> sourceRow = 242;
    }
    item trace_dff51f26bbd38512 : TraceRecord {
        attribute :>> elementId = "PORT::7211::电空转换阀指令输出::ITM-CMD-021::输出";
        attribute :>> sourceFile = "Rail_MBSE_Function_Interface_v1_final.xlsx";
        attribute :>> sourceSheet = "Interface";
        attribute :>> sourceRow = 243;
    }
    item trace_faa6c7c9931b0a58 : TraceRecord {
        attribute :>> elementId = "PORT::7211::紧急制动请求输入::ITM-CMD-004::输入";
        attribute :>> sourceFile = "Rail_MBSE_Function_Interface_v1_final.xlsx";
        attribute :>> sourceSheet = "Interface";
        attribute :>> sourceRow = 244;
    }
    item trace_ed944339b1333e10 : TraceRecord {
        attribute :>> elementId = "PORT::7211::车辆载荷系数输入::ITM-MEA-019::输入";
        attribute :>> sourceFile = "Rail_MBSE_Function_Interface_v1_final.xlsx";
        attribute :>> sourceSheet = "Interface";
        attribute :>> sourceRow = 245;
    }
    item trace_2885b328b968942b : TraceRecord {
        attribute :>> elementId = "PORT::7211::轮轨滑移率输入::ITM-MEA-020::输入";
        attribute :>> sourceFile = "Rail_MBSE_Function_Interface_v1_final.xlsx";
        attribute :>> sourceSheet = "Interface";
        attribute :>> sourceRow = 246;
    }
    item trace_91854864e6254d28 : TraceRecord {
        attribute :>> elementId = "PORT::7211::防滑干预指令输出::ITM-CMD-023::输出";
        attribute :>> sourceFile = "Rail_MBSE_Function_Interface_v1_final.xlsx";
        attribute :>> sourceSheet = "Interface";
        attribute :>> sourceRow = 247;
    }
    item trace_574d2a0f495ec049 : TraceRecord {
        attribute :>> elementId = "PORT::7211::防滑故障状态输出::ITM-STA-011::输出";
        attribute :>> sourceFile = "Rail_MBSE_Function_Interface_v1_final.xlsx";
        attribute :>> sourceSheet = "Interface";
        attribute :>> sourceRow = 248;
    }
    item trace_e71bf6c6a81443a2 : TraceRecord {
        attribute :>> elementId = "PORT::7211::防滑激活状态输出::ITM-STA-010::输出";
        attribute :>> sourceFile = "Rail_MBSE_Function_Interface_v1_final.xlsx";
        attribute :>> sourceSheet = "Interface";
        attribute :>> sourceRow = 249;
    }
    item trace_de41681b082603dc : TraceRecord {
        attribute :>> elementId = "PORT::7213::低压控制电能端口::ITM-PHY-015::双向物理";
        attribute :>> sourceFile = "Rail_MBSE_Function_Interface_v1_final.xlsx";
        attribute :>> sourceSheet = "Interface";
        attribute :>> sourceRow = 250;
    }
    item trace_de845d22bfa40612 : TraceRecord {
        attribute :>> elementId = "PORT::7213::制动控制接触器指令输入::ITM-CMD-031::输入";
        attribute :>> sourceFile = "Rail_MBSE_Function_Interface_v1_final.xlsx";
        attribute :>> sourceSheet = "Interface";
        attribute :>> sourceRow = 251;
    }
    item trace_a3e87ce99fd880b3 : TraceRecord {
        attribute :>> elementId = "PORT::7213::制动控制接触器状态输出::ITM-STA-036::输出";
        attribute :>> sourceFile = "Rail_MBSE_Function_Interface_v1_final.xlsx";
        attribute :>> sourceSheet = "Interface";
        attribute :>> sourceRow = 252;
    }
    item trace_d9d50ab5a08a26a5 : TraceRecord {
        attribute :>> elementId = "PORT::7222::主风压缩空气端口::ITM-PHY-008::双向物理";
        attribute :>> sourceFile = "Rail_MBSE_Function_Interface_v1_final.xlsx";
        attribute :>> sourceSheet = "Interface";
        attribute :>> sourceRow = 253;
    }
    item trace_43816dbefe351165 : TraceRecord {
        attribute :>> elementId = "PORT::7222::制动控制压缩空气端口::ITM-PHY-009::双向物理";
        attribute :>> sourceFile = "Rail_MBSE_Function_Interface_v1_final.xlsx";
        attribute :>> sourceSheet = "Interface";
        attribute :>> sourceRow = 254;
    }
    item trace_ddeea781987ee55c : TraceRecord {
        attribute :>> elementId = "PORT::7222::电空转换阀指令输入::ITM-CMD-021::输入";
        attribute :>> sourceFile = "Rail_MBSE_Function_Interface_v1_final.xlsx";
        attribute :>> sourceSheet = "Interface";
        attribute :>> sourceRow = 255;
    }
    item trace_4abc41bc202f61af : TraceRecord {
        attribute :>> elementId = "PORT::7223::主风压缩空气端口::ITM-PHY-008::双向物理";
        attribute :>> sourceFile = "Rail_MBSE_Function_Interface_v1_final.xlsx";
        attribute :>> sourceSheet = "Interface";
        attribute :>> sourceRow = 256;
    }
    item trace_9441f85d6ac8b0ed : TraceRecord {
        attribute :>> elementId = "PORT::7223::制动控制压缩空气端口::ITM-PHY-009::双向物理";
        attribute :>> sourceFile = "Rail_MBSE_Function_Interface_v1_final.xlsx";
        attribute :>> sourceSheet = "Interface";
        attribute :>> sourceRow = 257;
    }
    item trace_26b22e117179b62a : TraceRecord {
        attribute :>> elementId = "PORT::7223::制动缸压缩空气端口::ITM-PHY-010::双向物理";
        attribute :>> sourceFile = "Rail_MBSE_Function_Interface_v1_final.xlsx";
        attribute :>> sourceSheet = "Interface";
        attribute :>> sourceRow = 258;
    }
    item trace_291ee811748691f6 : TraceRecord {
        attribute :>> elementId = "PORT::7224::主风压缩空气端口::ITM-PHY-008::双向物理";
        attribute :>> sourceFile = "Rail_MBSE_Function_Interface_v1_final.xlsx";
        attribute :>> sourceSheet = "Interface";
        attribute :>> sourceRow = 259;
    }
    item trace_0714bcd5930c027b : TraceRecord {
        attribute :>> elementId = "PORT::7224::制动控制压缩空气端口::ITM-PHY-009::双向物理";
        attribute :>> sourceFile = "Rail_MBSE_Function_Interface_v1_final.xlsx";
        attribute :>> sourceSheet = "Interface";
        attribute :>> sourceRow = 260;
    }
    item trace_b9cbc1c18f711974 : TraceRecord {
        attribute :>> elementId = "PORT::7224::车辆载荷系数输入::ITM-MEA-019::输入";
        attribute :>> sourceFile = "Rail_MBSE_Function_Interface_v1_final.xlsx";
        attribute :>> sourceSheet = "Interface";
        attribute :>> sourceRow = 261;
    }
    item trace_f6a9fd98bacfc4e3 : TraceRecord {
        attribute :>> elementId = "PORT::7225::主风压缩空气端口::ITM-PHY-008::双向物理";
        attribute :>> sourceFile = "Rail_MBSE_Function_Interface_v1_final.xlsx";
        attribute :>> sourceSheet = "Interface";
        attribute :>> sourceRow = 262;
    }
    item trace_99bc109c3b70dfed : TraceRecord {
        attribute :>> elementId = "PORT::7225::制动控制压缩空气端口::ITM-PHY-009::双向物理";
        attribute :>> sourceFile = "Rail_MBSE_Function_Interface_v1_final.xlsx";
        attribute :>> sourceSheet = "Interface";
        attribute :>> sourceRow = 263;
    }
    item trace_8e705d6c34197ff6 : TraceRecord {
        attribute :>> elementId = "PORT::7225::制动电磁阀指令输入::ITM-CMD-022::输入";
        attribute :>> sourceFile = "Rail_MBSE_Function_Interface_v1_final.xlsx";
        attribute :>> sourceSheet = "Interface";
        attribute :>> sourceRow = 264;
    }
    item trace_5cccca40a5c3ac4f : TraceRecord {
        attribute :>> elementId = "PORT::7226::主风压缩空气端口::ITM-PHY-008::双向物理";
        attribute :>> sourceFile = "Rail_MBSE_Function_Interface_v1_final.xlsx";
        attribute :>> sourceSheet = "Interface";
        attribute :>> sourceRow = 265;
    }
    item trace_0f31359846cbf234 : TraceRecord {
        attribute :>> elementId = "PORT::7226::制动控制压缩空气端口::ITM-PHY-009::双向物理";
        attribute :>> sourceFile = "Rail_MBSE_Function_Interface_v1_final.xlsx";
        attribute :>> sourceSheet = "Interface";
        attribute :>> sourceRow = 266;
    }
    item trace_afce9ce1d2c43605 : TraceRecord {
        attribute :>> elementId = "PORT::7226::制动缸压缩空气端口::ITM-PHY-010::双向物理";
        attribute :>> sourceFile = "Rail_MBSE_Function_Interface_v1_final.xlsx";
        attribute :>> sourceSheet = "Interface";
        attribute :>> sourceRow = 267;
    }
    item trace_da93691eb6e6fca4 : TraceRecord {
        attribute :>> elementId = "PORT::7226::安全停车_制动请求输入::ITM-CMD-030::输入";
        attribute :>> sourceFile = "Rail_MBSE_Function_Interface_v1_final.xlsx";
        attribute :>> sourceSheet = "Interface";
        attribute :>> sourceRow = 268;
    }
    item trace_5f6a9d81cebde2d3 : TraceRecord {
        attribute :>> elementId = "PORT::7226::紧急制动请求输入::ITM-CMD-004::输入";
        attribute :>> sourceFile = "Rail_MBSE_Function_Interface_v1_final.xlsx";
        attribute :>> sourceSheet = "Interface";
        attribute :>> sourceRow = 269;
    }
    item trace_f645a5b55a3683c6 : TraceRecord {
        attribute :>> elementId = "PORT::7227::制动缓解指令输入::ITM-CMD-019::输入";
        attribute :>> sourceFile = "Rail_MBSE_Function_Interface_v1_final.xlsx";
        attribute :>> sourceSheet = "Interface";
        attribute :>> sourceRow = 270;
    }
    item trace_26311db59efd1104 : TraceRecord {
        attribute :>> elementId = "PORT::7227::制动缸压缩空气端口::ITM-PHY-010::双向物理";
        attribute :>> sourceFile = "Rail_MBSE_Function_Interface_v1_final.xlsx";
        attribute :>> sourceSheet = "Interface";
        attribute :>> sourceRow = 271;
    }
    item trace_8b8dde76f47ec820 : TraceRecord {
        attribute :>> elementId = "PORT::7228::制动隔离指令输入::ITM-CMD-020::输入";
        attribute :>> sourceFile = "Rail_MBSE_Function_Interface_v1_final.xlsx";
        attribute :>> sourceSheet = "Interface";
        attribute :>> sourceRow = 272;
    }
    item trace_3862b3383cf8bb5b : TraceRecord {
        attribute :>> elementId = "PORT::7228::制动隔离状态输出::ITM-STA-006::输出";
        attribute :>> sourceFile = "Rail_MBSE_Function_Interface_v1_final.xlsx";
        attribute :>> sourceSheet = "Interface";
        attribute :>> sourceRow = 273;
    }
    item trace_e8a2cfb94eeae29a : TraceRecord {
        attribute :>> elementId = "PORT::7228::第一气路制动缸压缩空气端口::ITM-PHY-010::双向物理";
        attribute :>> sourceFile = "Rail_MBSE_Function_Interface_v1_final.xlsx";
        attribute :>> sourceSheet = "Interface";
        attribute :>> sourceRow = 274;
    }
    item trace_9f256ce20a2eedba : TraceRecord {
        attribute :>> elementId = "PORT::7228::第二气路制动缸压缩空气端口::ITM-PHY-010::双向物理";
        attribute :>> sourceFile = "Rail_MBSE_Function_Interface_v1_final.xlsx";
        attribute :>> sourceSheet = "Interface";
        attribute :>> sourceRow = 275;
    }
    item trace_b38d34e10f750709 : TraceRecord {
        attribute :>> elementId = "PORT::7229::主风压缩空气端口::ITM-PHY-008::双向物理";
        attribute :>> sourceFile = "Rail_MBSE_Function_Interface_v1_final.xlsx";
        attribute :>> sourceSheet = "Interface";
        attribute :>> sourceRow = 276;
    }
    item trace_a8a0abe4af23248d : TraceRecord {
        attribute :>> elementId = "PORT::7229::制动控制压缩空气端口::ITM-PHY-009::双向物理";
        attribute :>> sourceFile = "Rail_MBSE_Function_Interface_v1_final.xlsx";
        attribute :>> sourceSheet = "Interface";
        attribute :>> sourceRow = 277;
    }
    item trace_1d96067b68d03c9c : TraceRecord {
        attribute :>> elementId = "PORT::722A::上游制动缸压缩空气端口::ITM-PHY-010::双向物理";
        attribute :>> sourceFile = "Rail_MBSE_Function_Interface_v1_final.xlsx";
        attribute :>> sourceSheet = "Interface";
        attribute :>> sourceRow = 278;
    }
    item trace_0093bc65af2a8f0a : TraceRecord {
        attribute :>> elementId = "PORT::722A::下游制动缸压缩空气端口::ITM-PHY-010::双向物理";
        attribute :>> sourceFile = "Rail_MBSE_Function_Interface_v1_final.xlsx";
        attribute :>> sourceSheet = "Interface";
        attribute :>> sourceRow = 279;
    }
    item trace_afe779aaa3b0be62 : TraceRecord {
        attribute :>> elementId = "PORT::722A::防滑干预指令输入::ITM-CMD-023::输入";
        attribute :>> sourceFile = "Rail_MBSE_Function_Interface_v1_final.xlsx";
        attribute :>> sourceSheet = "Interface";
        attribute :>> sourceRow = 280;
    }
    item trace_7d12c51f1034dc2f : TraceRecord {
        attribute :>> elementId = "PORT::722A::防滑故障状态输出::ITM-STA-011::输出";
        attribute :>> sourceFile = "Rail_MBSE_Function_Interface_v1_final.xlsx";
        attribute :>> sourceSheet = "Interface";
        attribute :>> sourceRow = 281;
    }
    item trace_396f6a682ced592d : TraceRecord {
        attribute :>> elementId = "PORT::722A::防滑激活状态输出::ITM-STA-010::输出";
        attribute :>> sourceFile = "Rail_MBSE_Function_Interface_v1_final.xlsx";
        attribute :>> sourceSheet = "Interface";
        attribute :>> sourceRow = 282;
    }
    item trace_8d219d5375ded80b : TraceRecord {
        attribute :>> elementId = "PORT::722B::制动缸压力输出::ITM-MEA-016::输出";
        attribute :>> sourceFile = "Rail_MBSE_Function_Interface_v1_final.xlsx";
        attribute :>> sourceSheet = "Interface";
        attribute :>> sourceRow = 283;
    }
    item trace_4861b172f136b92e : TraceRecord {
        attribute :>> elementId = "PORT::722B::制动缸压缩空气端口::ITM-PHY-010::双向物理";
        attribute :>> sourceFile = "Rail_MBSE_Function_Interface_v1_final.xlsx";
        attribute :>> sourceSheet = "Interface";
        attribute :>> sourceRow = 284;
    }
    item trace_6f3dd380decaae91 : TraceRecord {
        attribute :>> elementId = "PORT::722C::低风压状态输出::ITM-STA-009::输出";
        attribute :>> sourceFile = "Rail_MBSE_Function_Interface_v1_final.xlsx";
        attribute :>> sourceSheet = "Interface";
        attribute :>> sourceRow = 285;
    }
    item trace_041b8e496fc7f6c1 : TraceRecord {
        attribute :>> elementId = "PORT::722C::制动缸压缩空气端口::ITM-PHY-010::双向物理";
        attribute :>> sourceFile = "Rail_MBSE_Function_Interface_v1_final.xlsx";
        attribute :>> sourceSheet = "Interface";
        attribute :>> sourceRow = 286;
    }
    item trace_2a185ca8ff0ffb1b : TraceRecord {
        attribute :>> elementId = "PORT::7252::制动施加状态输出::ITM-STA-004::输出";
        attribute :>> sourceFile = "Rail_MBSE_Function_Interface_v1_final.xlsx";
        attribute :>> sourceSheet = "Interface";
        attribute :>> sourceRow = 287;
    }
    item trace_8c7b8a7b8f55d796 : TraceRecord {
        attribute :>> elementId = "PORT::7252::制动缓解状态输出::ITM-STA-005::输出";
        attribute :>> sourceFile = "Rail_MBSE_Function_Interface_v1_final.xlsx";
        attribute :>> sourceSheet = "Interface";
        attribute :>> sourceRow = 288;
    }
    item trace_7e02e65996d4ca82 : TraceRecord {
        attribute :>> elementId = "PORT::7252::制动缸压缩空气端口::ITM-PHY-010::双向物理";
        attribute :>> sourceFile = "Rail_MBSE_Function_Interface_v1_final.xlsx";
        attribute :>> sourceSheet = "Interface";
        attribute :>> sourceRow = 289;
    }
    item trace_6e046e892954d0de : TraceRecord {
        attribute :>> elementId = "PORT::7252::实际摩擦制动力输出::ITM-MEA-017::输出";
        attribute :>> sourceFile = "Rail_MBSE_Function_Interface_v1_final.xlsx";
        attribute :>> sourceSheet = "Interface";
        attribute :>> sourceRow = 290;
    }
    item trace_b403e112a25e1c53 : TraceRecord {
        attribute :>> elementId = "PORT::7252::摩擦制动机械作用端口::ITM-PHY-007::双向物理";
        attribute :>> sourceFile = "Rail_MBSE_Function_Interface_v1_final.xlsx";
        attribute :>> sourceSheet = "Interface";
        attribute :>> sourceRow = 291;
    }
    item trace_d9511ef0fa1c17df : TraceRecord {
        attribute :>> elementId = "PORT::7254::摩擦制动机械作用端口::ITM-PHY-007::双向物理";
        attribute :>> sourceFile = "Rail_MBSE_Function_Interface_v1_final.xlsx";
        attribute :>> sourceSheet = "Interface";
        attribute :>> sourceRow = 292;
    }
    item trace_7823b5bc99189b72 : TraceRecord {
        attribute :>> elementId = "PORT::7254::摩擦制动耗散功率输出::ITM-ACC-006::输出";
        attribute :>> sourceFile = "Rail_MBSE_Function_Interface_v1_final.xlsx";
        attribute :>> sourceSheet = "Interface";
        attribute :>> sourceRow = 293;
    }
    item trace_02c0f1010de52783 : TraceRecord {
        attribute :>> elementId = "PORT::7254::摩擦制动耗散累计能量输出::ITM-ACC-013::输出";
        attribute :>> sourceFile = "Rail_MBSE_Function_Interface_v1_final.xlsx";
        attribute :>> sourceSheet = "Interface";
        attribute :>> sourceRow = 294;
    }
    item trace_a60f1e83b03ea6d4 : TraceRecord {
        attribute :>> elementId = "PORT::7254::热能_热流端口::ITM-PHY-013::双向物理";
        attribute :>> sourceFile = "Rail_MBSE_Function_Interface_v1_final.xlsx";
        attribute :>> sourceSheet = "Interface";
        attribute :>> sourceRow = 295;
    }
    item trace_734246fb536f2b68 : TraceRecord {
        attribute :>> elementId = "PORT::7255::制动缸压缩空气端口::ITM-PHY-010::双向物理";
        attribute :>> sourceFile = "Rail_MBSE_Function_Interface_v1_final.xlsx";
        attribute :>> sourceSheet = "Interface";
        attribute :>> sourceRow = 296;
    }
    item trace_4c45e349056154be : TraceRecord {
        attribute :>> elementId = "PORT::7255::摩擦制动机械作用端口::ITM-PHY-007::双向物理";
        attribute :>> sourceFile = "Rail_MBSE_Function_Interface_v1_final.xlsx";
        attribute :>> sourceSheet = "Interface";
        attribute :>> sourceRow = 297;
    }
    item trace_2e35e3bc261ab52a : TraceRecord {
        attribute :>> elementId = "PORT::7281::低压控制电能端口::ITM-PHY-015::双向物理";
        attribute :>> sourceFile = "Rail_MBSE_Function_Interface_v1_final.xlsx";
        attribute :>> sourceSheet = "Interface";
        attribute :>> sourceRow = 298;
    }
    item trace_b9ead4720ad37cb5 : TraceRecord {
        attribute :>> elementId = "PORT::7281::制动施加状态输入::ITM-STA-004::输入";
        attribute :>> sourceFile = "Rail_MBSE_Function_Interface_v1_final.xlsx";
        attribute :>> sourceSheet = "Interface";
        attribute :>> sourceRow = 299;
    }
    item trace_28b3abdb6d1d1e9e : TraceRecord {
        attribute :>> elementId = "PORT::7281::制动缓解状态输入::ITM-STA-005::输入";
        attribute :>> sourceFile = "Rail_MBSE_Function_Interface_v1_final.xlsx";
        attribute :>> sourceSheet = "Interface";
        attribute :>> sourceRow = 300;
    }
    item trace_5158f71b0a56da87 : TraceRecord {
        attribute :>> elementId = "PORT::7281::制动隔离状态输入::ITM-STA-006::输入";
        attribute :>> sourceFile = "Rail_MBSE_Function_Interface_v1_final.xlsx";
        attribute :>> sourceSheet = "Interface";
        attribute :>> sourceRow = 301;
    }
    item trace_0b1d53051662d3f2 : TraceRecord {
        attribute :>> elementId = "PORT::7284::制动隔离指令输入::ITM-CMD-020::输入";
        attribute :>> sourceFile = "Rail_MBSE_Function_Interface_v1_final.xlsx";
        attribute :>> sourceSheet = "Interface";
        attribute :>> sourceRow = 302;
    }
    item trace_2e5b4d181eadc747 : TraceRecord {
        attribute :>> elementId = "PORT::7284::制动隔离状态输出::ITM-STA-006::输出";
        attribute :>> sourceFile = "Rail_MBSE_Function_Interface_v1_final.xlsx";
        attribute :>> sourceSheet = "Interface";
        attribute :>> sourceRow = 303;
    }
    item trace_c958e15a33eb790f : TraceRecord {
        attribute :>> elementId = "PORT::7284::第一气路制动缸压缩空气端口::ITM-PHY-010::双向物理";
        attribute :>> sourceFile = "Rail_MBSE_Function_Interface_v1_final.xlsx";
        attribute :>> sourceSheet = "Interface";
        attribute :>> sourceRow = 304;
    }
    item trace_3e963340985cb7bd : TraceRecord {
        attribute :>> elementId = "PORT::7284::第二气路制动缸压缩空气端口::ITM-PHY-010::双向物理";
        attribute :>> sourceFile = "Rail_MBSE_Function_Interface_v1_final.xlsx";
        attribute :>> sourceSheet = "Interface";
        attribute :>> sourceRow = 305;
    }
    item trace_c016d56a46e739fc : TraceRecord {
        attribute :>> elementId = "PORT::7285::制动隔离指令输入::ITM-CMD-020::输入";
        attribute :>> sourceFile = "Rail_MBSE_Function_Interface_v1_final.xlsx";
        attribute :>> sourceSheet = "Interface";
        attribute :>> sourceRow = 306;
    }
    item trace_47c1a16735a84ed9 : TraceRecord {
        attribute :>> elementId = "PORT::7285::制动隔离状态输出::ITM-STA-006::输出";
        attribute :>> sourceFile = "Rail_MBSE_Function_Interface_v1_final.xlsx";
        attribute :>> sourceSheet = "Interface";
        attribute :>> sourceRow = 307;
    }
    item trace_73c5051041203267 : TraceRecord {
        attribute :>> elementId = "PORT::7285::第一气路制动缸压缩空气端口::ITM-PHY-010::双向物理";
        attribute :>> sourceFile = "Rail_MBSE_Function_Interface_v1_final.xlsx";
        attribute :>> sourceSheet = "Interface";
        attribute :>> sourceRow = 308;
    }
    item trace_337ee35177e1c114 : TraceRecord {
        attribute :>> elementId = "PORT::7285::第二气路制动缸压缩空气端口::ITM-PHY-010::双向物理";
        attribute :>> sourceFile = "Rail_MBSE_Function_Interface_v1_final.xlsx";
        attribute :>> sourceSheet = "Interface";
        attribute :>> sourceRow = 309;
    }
    item trace_d5423b06aaccb6ac : TraceRecord {
        attribute :>> elementId = "PORT::8121::ATP_外部安全系统状态输入::ITM-STA-027::输入";
        attribute :>> sourceFile = "Rail_MBSE_Function_Interface_v1_final.xlsx";
        attribute :>> sourceSheet = "Interface";
        attribute :>> sourceRow = 310;
    }
    item trace_d2dfdd1f41baec7a : TraceRecord {
        attribute :>> elementId = "PORT::8121::低压控制电能端口::ITM-PHY-015::双向物理";
        attribute :>> sourceFile = "Rail_MBSE_Function_Interface_v1_final.xlsx";
        attribute :>> sourceSheet = "Interface";
        attribute :>> sourceRow = 311;
    }
    item trace_2ee1cd48c6d41ac7 : TraceRecord {
        attribute :>> elementId = "PORT::8121::列车方向指令输入::ITM-CMD-001::输入";
        attribute :>> sourceFile = "Rail_MBSE_Function_Interface_v1_final.xlsx";
        attribute :>> sourceSheet = "Interface";
        attribute :>> sourceRow = 312;
    }
    item trace_8fbe2a98ba0ac28c : TraceRecord {
        attribute :>> elementId = "PORT::8121::列车方向指令输出::ITM-CMD-001::输出";
        attribute :>> sourceFile = "Rail_MBSE_Function_Interface_v1_final.xlsx";
        attribute :>> sourceSheet = "Interface";
        attribute :>> sourceRow = 313;
    }
    item trace_ef398de483959e24 : TraceRecord {
        attribute :>> elementId = "PORT::8121::列车速度输入::ITM-MEA-001::输入";
        attribute :>> sourceFile = "Rail_MBSE_Function_Interface_v1_final.xlsx";
        attribute :>> sourceSheet = "Interface";
        attribute :>> sourceRow = 314;
    }
    item trace_36991cec1f7be17b : TraceRecord {
        attribute :>> elementId = "PORT::8121::制动安全回路状态输入::ITM-STA-025::输入";
        attribute :>> sourceFile = "Rail_MBSE_Function_Interface_v1_final.xlsx";
        attribute :>> sourceSheet = "Interface";
        attribute :>> sourceRow = 315;
    }
    item trace_1c14ea3cdc439198 : TraceRecord {
        attribute :>> elementId = "PORT::8121::制动系统可用状态输入::ITM-STA-003::输入";
        attribute :>> sourceFile = "Rail_MBSE_Function_Interface_v1_final.xlsx";
        attribute :>> sourceSheet = "Interface";
        attribute :>> sourceRow = 316;
    }
    item trace_4325db72e2d88769 : TraceRecord {
        attribute :>> elementId = "PORT::8121::安全停车_制动请求输入::ITM-CMD-030::输入";
        attribute :>> sourceFile = "Rail_MBSE_Function_Interface_v1_final.xlsx";
        attribute :>> sourceSheet = "Interface";
        attribute :>> sourceRow = 317;
    }
    item trace_0b58c63caeaf2f6d : TraceRecord {
        attribute :>> elementId = "PORT::8121::服务制动请求输入::ITM-CMD-003::输入";
        attribute :>> sourceFile = "Rail_MBSE_Function_Interface_v1_final.xlsx";
        attribute :>> sourceSheet = "Interface";
        attribute :>> sourceRow = 318;
    }
    item trace_d82e5c8a7afb4b7b : TraceRecord {
        attribute :>> elementId = "PORT::8121::服务制动请求输出::ITM-CMD-003::输出";
        attribute :>> sourceFile = "Rail_MBSE_Function_Interface_v1_final.xlsx";
        attribute :>> sourceSheet = "Interface";
        attribute :>> sourceRow = 319;
    }
    item trace_f4c8eaaf49d11d3d : TraceRecord {
        attribute :>> elementId = "PORT::8121::牵引使能指令输出::ITM-CMD-009::输出";
        attribute :>> sourceFile = "Rail_MBSE_Function_Interface_v1_final.xlsx";
        attribute :>> sourceSheet = "Interface";
        attribute :>> sourceRow = 320;
    }
    item trace_c49f12594ff56025 : TraceRecord {
        attribute :>> elementId = "PORT::8121::牵引切除请求输出::ITM-CMD-008::输出";
        attribute :>> sourceFile = "Rail_MBSE_Function_Interface_v1_final.xlsx";
        attribute :>> sourceSheet = "Interface";
        attribute :>> sourceRow = 321;
    }
    item trace_37e2c2d63c55e098 : TraceRecord {
        attribute :>> elementId = "PORT::8121::牵引可用状态输入::ITM-STA-001::输入";
        attribute :>> sourceFile = "Rail_MBSE_Function_Interface_v1_final.xlsx";
        attribute :>> sourceSheet = "Interface";
        attribute :>> sourceRow = 322;
    }
    item trace_de2d35d2bcb08b0b : TraceRecord {
        attribute :>> elementId = "PORT::8121::牵引安全回路状态输入::ITM-STA-026::输入";
        attribute :>> sourceFile = "Rail_MBSE_Function_Interface_v1_final.xlsx";
        attribute :>> sourceSheet = "Interface";
        attribute :>> sourceRow = 323;
    }
    item trace_a49a67fafe112278 : TraceRecord {
        attribute :>> elementId = "PORT::8121::牵引指令输入::ITM-CMD-002::输入";
        attribute :>> sourceFile = "Rail_MBSE_Function_Interface_v1_final.xlsx";
        attribute :>> sourceSheet = "Interface";
        attribute :>> sourceRow = 324;
    }
    item trace_809f8275c004ab18 : TraceRecord {
        attribute :>> elementId = "PORT::8121::牵引指令输出::ITM-CMD-002::输出";
        attribute :>> sourceFile = "Rail_MBSE_Function_Interface_v1_final.xlsx";
        attribute :>> sourceSheet = "Interface";
        attribute :>> sourceRow = 325;
    }
    item trace_1e34bb2697325127 : TraceRecord {
        attribute :>> elementId = "PORT::8121::紧急制动请求输入::ITM-CMD-004::输入";
        attribute :>> sourceFile = "Rail_MBSE_Function_Interface_v1_final.xlsx";
        attribute :>> sourceSheet = "Interface";
        attribute :>> sourceRow = 326;
    }
    item trace_a9c7eff84933cd80 : TraceRecord {
        attribute :>> elementId = "PORT::8121::紧急制动请求输出::ITM-CMD-004::输出";
        attribute :>> sourceFile = "Rail_MBSE_Function_Interface_v1_final.xlsx";
        attribute :>> sourceSheet = "Interface";
        attribute :>> sourceRow = 327;
    }
    item trace_2455eff74badb007 : TraceRecord {
        attribute :>> elementId = "PORT::8121::高压安全回路状态输入::ITM-STA-024::输入";
        attribute :>> sourceFile = "Rail_MBSE_Function_Interface_v1_final.xlsx";
        attribute :>> sourceSheet = "Interface";
        attribute :>> sourceRow = 328;
    }
    item trace_361eac651ec9fd05 : TraceRecord {
        attribute :>> elementId = "PORT::8122::中间直流母线电压输入::ITM-MEA-008::输入";
        attribute :>> sourceFile = "Rail_MBSE_Function_Interface_v1_final.xlsx";
        attribute :>> sourceSheet = "Interface";
        attribute :>> sourceRow = 329;
    }
    item trace_8b55477454952732 : TraceRecord {
        attribute :>> elementId = "PORT::8122::低压控制电能端口::ITM-PHY-015::双向物理";
        attribute :>> sourceFile = "Rail_MBSE_Function_Interface_v1_final.xlsx";
        attribute :>> sourceSheet = "Interface";
        attribute :>> sourceRow = 330;
    }
    item trace_4683a7cb63e55daf : TraceRecord {
        attribute :>> elementId = "PORT::8122::储能主接触器指令输出::ITM-CMD-027::输出";
        attribute :>> sourceFile = "Rail_MBSE_Function_Interface_v1_final.xlsx";
        attribute :>> sourceSheet = "Interface";
        attribute :>> sourceRow = 331;
    }
    item trace_77c439392dea95b4 : TraceRecord {
        attribute :>> elementId = "PORT::8122::储能功率请求输出::ITM-CMD-025::输出";
        attribute :>> sourceFile = "Rail_MBSE_Function_Interface_v1_final.xlsx";
        attribute :>> sourceSheet = "Interface";
        attribute :>> sourceRow = 332;
    }
    item trace_8c3ed075d33335e8 : TraceRecord {
        attribute :>> elementId = "PORT::8122::储能可用充电功率输入::ITM-LIM-009::输入";
        attribute :>> sourceFile = "Rail_MBSE_Function_Interface_v1_final.xlsx";
        attribute :>> sourceSheet = "Interface";
        attribute :>> sourceRow = 333;
    }
    item trace_35b0ef67b409e840 : TraceRecord {
        attribute :>> elementId = "PORT::8122::储能可用放电功率输入::ITM-LIM-010::输入";
        attribute :>> sourceFile = "Rail_MBSE_Function_Interface_v1_final.xlsx";
        attribute :>> sourceSheet = "Interface";
        attribute :>> sourceRow = 334;
    }
    item trace_a095b9b42ab5cc7d : TraceRecord {
        attribute :>> elementId = "PORT::8122::储能吸收功率输入::ITM-ACC-004::输入";
        attribute :>> sourceFile = "Rail_MBSE_Function_Interface_v1_final.xlsx";
        attribute :>> sourceSheet = "Interface";
        attribute :>> sourceRow = 335;
    }
    item trace_47c78247980cc3a5 : TraceRecord {
        attribute :>> elementId = "PORT::8122::储能故障复位指令输出::ITM-CMD-029::输出";
        attribute :>> sourceFile = "Rail_MBSE_Function_Interface_v1_final.xlsx";
        attribute :>> sourceSheet = "Interface";
        attribute :>> sourceRow = 336;
    }
    item trace_1967a947dd39d4a5 : TraceRecord {
        attribute :>> elementId = "PORT::8122::储能系统可用状态输入::ITM-STA-030::输入";
        attribute :>> sourceFile = "Rail_MBSE_Function_Interface_v1_final.xlsx";
        attribute :>> sourceSheet = "Interface";
        attribute :>> sourceRow = 337;
    }
    item trace_9d3500c169fe7103 : TraceRecord {
        attribute :>> elementId = "PORT::8122::储能系统故障状态输入::ITM-STA-031::输入";
        attribute :>> sourceFile = "Rail_MBSE_Function_Interface_v1_final.xlsx";
        attribute :>> sourceSheet = "Interface";
        attribute :>> sourceRow = 338;
    }
    item trace_f704c2e7bab06749 : TraceRecord {
        attribute :>> elementId = "PORT::8122::储能预充电指令输出::ITM-CMD-028::输出";
        attribute :>> sourceFile = "Rail_MBSE_Function_Interface_v1_final.xlsx";
        attribute :>> sourceSheet = "Interface";
        attribute :>> sourceRow = 339;
    }
    item trace_3aaf955421310ab3 : TraceRecord {
        attribute :>> elementId = "PORT::8122::再生功率上限输入::ITM-LIM-004::输入";
        attribute :>> sourceFile = "Rail_MBSE_Function_Interface_v1_final.xlsx";
        attribute :>> sourceSheet = "Interface";
        attribute :>> sourceRow = 340;
    }
    item trace_ac60006ecd824aae : TraceRecord {
        attribute :>> elementId = "PORT::8122::列车方向指令输入::ITM-CMD-001::输入";
        attribute :>> sourceFile = "Rail_MBSE_Function_Interface_v1_final.xlsx";
        attribute :>> sourceSheet = "Interface";
        attribute :>> sourceRow = 341;
    }
    item trace_03fc81b8fdcfa7b2 : TraceRecord {
        attribute :>> elementId = "PORT::8122::列车速度输入::ITM-MEA-001::输入";
        attribute :>> sourceFile = "Rail_MBSE_Function_Interface_v1_final.xlsx";
        attribute :>> sourceSheet = "Interface";
        attribute :>> sourceRow = 342;
    }
    item trace_dae173a1561f3f35 : TraceRecord {
        attribute :>> elementId = "PORT::8122::制动电阻耗散功率输入::ITM-ACC-005::输入";
        attribute :>> sourceFile = "Rail_MBSE_Function_Interface_v1_final.xlsx";
        attribute :>> sourceSheet = "Interface";
        attribute :>> sourceRow = 343;
    }
    item trace_b1fb8856841fb7cf : TraceRecord {
        attribute :>> elementId = "PORT::8122::制动系统可用状态输入::ITM-STA-003::输入";
        attribute :>> sourceFile = "Rail_MBSE_Function_Interface_v1_final.xlsx";
        attribute :>> sourceSheet = "Interface";
        attribute :>> sourceRow = 344;
    }
    item trace_ca63e6a6492a217f : TraceRecord {
        attribute :>> elementId = "PORT::8122::动态制动可用状态输入::ITM-STA-002::输入";
        attribute :>> sourceFile = "Rail_MBSE_Function_Interface_v1_final.xlsx";
        attribute :>> sourceSheet = "Interface";
        attribute :>> sourceRow = 345;
    }
    item trace_a4aac084c46e1e57 : TraceRecord {
        attribute :>> elementId = "PORT::8122::双向DC_DC使能输出::ITM-CMD-026::输出";
        attribute :>> sourceFile = "Rail_MBSE_Function_Interface_v1_final.xlsx";
        attribute :>> sourceSheet = "Interface";
        attribute :>> sourceRow = 346;
    }
    item trace_e1808e35289aaba6 : TraceRecord {
        attribute :>> elementId = "PORT::8122::双向DC_DC实际功率输入::ITM-MEA-029::输入";
        attribute :>> sourceFile = "Rail_MBSE_Function_Interface_v1_final.xlsx";
        attribute :>> sourceSheet = "Interface";
        attribute :>> sourceRow = 347;
    }
    item trace_e0814e233fa0db3e : TraceRecord {
        attribute :>> elementId = "PORT::8122::可用动态制动力输入::ITM-LIM-001::输入";
        attribute :>> sourceFile = "Rail_MBSE_Function_Interface_v1_final.xlsx";
        attribute :>> sourceSheet = "Interface";
        attribute :>> sourceRow = 348;
    }
    item trace_eb1cf5594b5796be : TraceRecord {
        attribute :>> elementId = "PORT::8122::回馈电网功率输入::ITM-ACC-003::输入";
        attribute :>> sourceFile = "Rail_MBSE_Function_Interface_v1_final.xlsx";
        attribute :>> sourceSheet = "Interface";
        attribute :>> sourceRow = 349;
    }
    item trace_ab848f3c1a74117a : TraceRecord {
        attribute :>> elementId = "PORT::8122::安全停车_制动请求输入::ITM-CMD-030::输入";
        attribute :>> sourceFile = "Rail_MBSE_Function_Interface_v1_final.xlsx";
        attribute :>> sourceSheet = "Interface";
        attribute :>> sourceRow = 350;
    }
    item trace_bd78e8d84d334672 : TraceRecord {
        attribute :>> elementId = "PORT::8122::实际再生功率输入::ITM-ACC-002::输入";
        attribute :>> sourceFile = "Rail_MBSE_Function_Interface_v1_final.xlsx";
        attribute :>> sourceSheet = "Interface";
        attribute :>> sourceRow = 351;
    }
    item trace_f36629c6f163833f : TraceRecord {
        attribute :>> elementId = "PORT::8122::实际动态制动力输入::ITM-MEA-013::输入";
        attribute :>> sourceFile = "Rail_MBSE_Function_Interface_v1_final.xlsx";
        attribute :>> sourceSheet = "Interface";
        attribute :>> sourceRow = 352;
    }
    item trace_abc36140248d0eef : TraceRecord {
        attribute :>> elementId = "PORT::8122::接触网可接收功率输入::ITM-LIM-005::输入";
        attribute :>> sourceFile = "Rail_MBSE_Function_Interface_v1_final.xlsx";
        attribute :>> sourceSheet = "Interface";
        attribute :>> sourceRow = 353;
    }
    item trace_f0886e48bf75472f : TraceRecord {
        attribute :>> elementId = "PORT::8122::撒砂请求输出::ITM-CMD-024::输出";
        attribute :>> sourceFile = "Rail_MBSE_Function_Interface_v1_final.xlsx";
        attribute :>> sourceSheet = "Interface";
        attribute :>> sourceRow = 354;
    }
    item trace_898e3aba50ea7cb4 : TraceRecord {
        attribute :>> elementId = "PORT::8122::服务制动请求输入::ITM-CMD-003::输入";
        attribute :>> sourceFile = "Rail_MBSE_Function_Interface_v1_final.xlsx";
        attribute :>> sourceSheet = "Interface";
        attribute :>> sourceRow = 355;
    }
    item trace_43a34d07ce05b457 : TraceRecord {
        attribute :>> elementId = "PORT::8122::牵引使能指令输出::ITM-CMD-009::输出";
        attribute :>> sourceFile = "Rail_MBSE_Function_Interface_v1_final.xlsx";
        attribute :>> sourceSheet = "Interface";
        attribute :>> sourceRow = 356;
    }
    item trace_7df2943f24bd3f24 : TraceRecord {
        attribute :>> elementId = "PORT::8122::牵引切除请求输出::ITM-CMD-008::输出";
        attribute :>> sourceFile = "Rail_MBSE_Function_Interface_v1_final.xlsx";
        attribute :>> sourceSheet = "Interface";
        attribute :>> sourceRow = 357;
    }
    item trace_81e596aab3f0fe4c : TraceRecord {
        attribute :>> elementId = "PORT::8122::牵引变流器故障状态输入::ITM-STA-019::输入";
        attribute :>> sourceFile = "Rail_MBSE_Function_Interface_v1_final.xlsx";
        attribute :>> sourceSheet = "Interface";
        attribute :>> sourceRow = 358;
    }
    item trace_b6a69bd683685d04 : TraceRecord {
        attribute :>> elementId = "PORT::8122::牵引可用状态输入::ITM-STA-001::输入";
        attribute :>> sourceFile = "Rail_MBSE_Function_Interface_v1_final.xlsx";
        attribute :>> sourceSheet = "Interface";
        attribute :>> sourceRow = 359;
    }
    item trace_c39f0a202834bb12 : TraceRecord {
        attribute :>> elementId = "PORT::8122::牵引指令输入::ITM-CMD-002::输入";
        attribute :>> sourceFile = "Rail_MBSE_Function_Interface_v1_final.xlsx";
        attribute :>> sourceSheet = "Interface";
        attribute :>> sourceRow = 360;
    }
    item trace_361e7dc74e9287e3 : TraceRecord {
        attribute :>> elementId = "PORT::8122::紧急制动请求输入::ITM-CMD-004::输入";
        attribute :>> sourceFile = "Rail_MBSE_Function_Interface_v1_final.xlsx";
        attribute :>> sourceSheet = "Interface";
        attribute :>> sourceRow = 361;
    }
    item trace_b11b9e2ada11927e : TraceRecord {
        attribute :>> elementId = "PORT::8122::能量回收率输入::ITM-ACC-015::输入";
        attribute :>> sourceFile = "Rail_MBSE_Function_Interface_v1_final.xlsx";
        attribute :>> sourceSheet = "Interface";
        attribute :>> sourceRow = 362;
    }
    item trace_6437aa0577c9ccd7 : TraceRecord {
        attribute :>> elementId = "PORT::8122::超级电容SOC输入::ITM-MEA-028::输入";
        attribute :>> sourceFile = "Rail_MBSE_Function_Interface_v1_final.xlsx";
        attribute :>> sourceSheet = "Interface";
        attribute :>> sourceRow = 363;
    }
    item trace_7262595caaf3b8d8 : TraceRecord {
        attribute :>> elementId = "PORT::8125::中间直流母线电压输入::ITM-MEA-008::输入";
        attribute :>> sourceFile = "Rail_MBSE_Function_Interface_v1_final.xlsx";
        attribute :>> sourceSheet = "Interface";
        attribute :>> sourceRow = 364;
    }
    item trace_5184547f4558dae5 : TraceRecord {
        attribute :>> elementId = "PORT::8125::低压控制电能端口::ITM-PHY-015::双向物理";
        attribute :>> sourceFile = "Rail_MBSE_Function_Interface_v1_final.xlsx";
        attribute :>> sourceSheet = "Interface";
        attribute :>> sourceRow = 365;
    }
    item trace_91d8f479934c65da : TraceRecord {
        attribute :>> elementId = "PORT::8125::再生功率上限输出::ITM-LIM-004::输出";
        attribute :>> sourceFile = "Rail_MBSE_Function_Interface_v1_final.xlsx";
        attribute :>> sourceSheet = "Interface";
        attribute :>> sourceRow = 366;
    }
    item trace_4cfbda9683c8c299 : TraceRecord {
        attribute :>> elementId = "PORT::8125::列车速度输入::ITM-MEA-001::输入";
        attribute :>> sourceFile = "Rail_MBSE_Function_Interface_v1_final.xlsx";
        attribute :>> sourceSheet = "Interface";
        attribute :>> sourceRow = 367;
    }
    item trace_d69905c106b65d8f : TraceRecord {
        attribute :>> elementId = "PORT::8125::动态制动力请求输入::ITM-CMD-006::输入";
        attribute :>> sourceFile = "Rail_MBSE_Function_Interface_v1_final.xlsx";
        attribute :>> sourceSheet = "Interface";
        attribute :>> sourceRow = 368;
    }
    item trace_dae11d7502a6c37a : TraceRecord {
        attribute :>> elementId = "PORT::8125::动态制动可用状态输出::ITM-STA-002::输出";
        attribute :>> sourceFile = "Rail_MBSE_Function_Interface_v1_final.xlsx";
        attribute :>> sourceSheet = "Interface";
        attribute :>> sourceRow = 369;
    }
    item trace_b60dd66dcfd10afa : TraceRecord {
        attribute :>> elementId = "PORT::8125::可用动态制动力输出::ITM-LIM-001::输出";
        attribute :>> sourceFile = "Rail_MBSE_Function_Interface_v1_final.xlsx";
        attribute :>> sourceSheet = "Interface";
        attribute :>> sourceRow = 370;
    }
    item trace_36a59f5828d4c515 : TraceRecord {
        attribute :>> elementId = "PORT::8125::实际动态制动力输出::ITM-MEA-013::输出";
        attribute :>> sourceFile = "Rail_MBSE_Function_Interface_v1_final.xlsx";
        attribute :>> sourceSheet = "Interface";
        attribute :>> sourceRow = 371;
    }
    item trace_1809c94f1581c7f8 : TraceRecord {
        attribute :>> elementId = "PORT::8125::接触网可接收功率输入::ITM-LIM-005::输入";
        attribute :>> sourceFile = "Rail_MBSE_Function_Interface_v1_final.xlsx";
        attribute :>> sourceSheet = "Interface";
        attribute :>> sourceRow = 372;
    }
    item trace_19dfe907fce085c5 : TraceRecord {
        attribute :>> elementId = "PORT::8125::牵引_再生转矩上限输出::ITM-LIM-003::输出";
        attribute :>> sourceFile = "Rail_MBSE_Function_Interface_v1_final.xlsx";
        attribute :>> sourceSheet = "Interface";
        attribute :>> sourceRow = 373;
    }
    item trace_0e01f3a589418f6c : TraceRecord {
        attribute :>> elementId = "PORT::8125::牵引使能指令输入::ITM-CMD-009::输入";
        attribute :>> sourceFile = "Rail_MBSE_Function_Interface_v1_final.xlsx";
        attribute :>> sourceSheet = "Interface";
        attribute :>> sourceRow = 374;
    }
    item trace_d86bd7909c634e71 : TraceRecord {
        attribute :>> elementId = "PORT::8125::牵引切除请求输入::ITM-CMD-008::输入";
        attribute :>> sourceFile = "Rail_MBSE_Function_Interface_v1_final.xlsx";
        attribute :>> sourceSheet = "Interface";
        attribute :>> sourceRow = 375;
    }
    item trace_03e482bfcbcb37c1 : TraceRecord {
        attribute :>> elementId = "PORT::8125::牵引变流器故障状态输出::ITM-STA-019::输出";
        attribute :>> sourceFile = "Rail_MBSE_Function_Interface_v1_final.xlsx";
        attribute :>> sourceSheet = "Interface";
        attribute :>> sourceRow = 376;
    }
    item trace_04f0621818e40445 : TraceRecord {
        attribute :>> elementId = "PORT::8125::牵引可用状态输出::ITM-STA-001::输出";
        attribute :>> sourceFile = "Rail_MBSE_Function_Interface_v1_final.xlsx";
        attribute :>> sourceSheet = "Interface";
        attribute :>> sourceRow = 377;
    }
    item trace_90deb6e5a4e470f1 : TraceRecord {
        attribute :>> elementId = "PORT::8125::牵引安全回路状态输入::ITM-STA-026::输入";
        attribute :>> sourceFile = "Rail_MBSE_Function_Interface_v1_final.xlsx";
        attribute :>> sourceSheet = "Interface";
        attribute :>> sourceRow = 378;
    }
    item trace_713c697d47d94da9 : TraceRecord {
        attribute :>> elementId = "PORT::8125::牵引指令输入::ITM-CMD-002::输入";
        attribute :>> sourceFile = "Rail_MBSE_Function_Interface_v1_final.xlsx";
        attribute :>> sourceSheet = "Interface";
        attribute :>> sourceRow = 379;
    }
    item trace_1faca3fc4ff0e741 : TraceRecord {
        attribute :>> elementId = "PORT::8125::牵引电机实际转矩输入::ITM-MEA-012::输入";
        attribute :>> sourceFile = "Rail_MBSE_Function_Interface_v1_final.xlsx";
        attribute :>> sourceSheet = "Interface";
        attribute :>> sourceRow = 380;
    }
    item trace_70a8e2c4b0887b4d : TraceRecord {
        attribute :>> elementId = "PORT::8125::牵引电机转矩请求输出::ITM-CMD-012::输出";
        attribute :>> sourceFile = "Rail_MBSE_Function_Interface_v1_final.xlsx";
        attribute :>> sourceSheet = "Interface";
        attribute :>> sourceRow = 381;
    }
    item trace_4e582bfad9ebbf1d : TraceRecord {
        attribute :>> elementId = "PORT::8125::牵引电机转速输入::ITM-MEA-004::输入";
        attribute :>> sourceFile = "Rail_MBSE_Function_Interface_v1_final.xlsx";
        attribute :>> sourceSheet = "Interface";
        attribute :>> sourceRow = 382;
    }
    item trace_0964720b73edce27 : TraceRecord {
        attribute :>> elementId = "PORT::8125::电机侧变流器状态输出::ITM-STA-018::输出";
        attribute :>> sourceFile = "Rail_MBSE_Function_Interface_v1_final.xlsx";
        attribute :>> sourceSheet = "Interface";
        attribute :>> sourceRow = 383;
    }
    item trace_aa028339300f4dbf : TraceRecord {
        attribute :>> elementId = "PORT::8125::网侧变流器状态输出::ITM-STA-017::输出";
        attribute :>> sourceFile = "Rail_MBSE_Function_Interface_v1_final.xlsx";
        attribute :>> sourceSheet = "Interface";
        attribute :>> sourceRow = 384;
    }
    item trace_a916a9847aeadebb : TraceRecord {
        attribute :>> elementId = "PORT::8127::ATP_外部安全系统状态输入::ITM-STA-027::输入";
        attribute :>> sourceFile = "Rail_MBSE_Function_Interface_v1_final.xlsx";
        attribute :>> sourceSheet = "Interface";
        attribute :>> sourceRow = 385;
    }
    item trace_a5398c912a371abd : TraceRecord {
        attribute :>> elementId = "PORT::8127::ATP_外部安全系统状态输出::ITM-STA-027::输出";
        attribute :>> sourceFile = "Rail_MBSE_Function_Interface_v1_final.xlsx";
        attribute :>> sourceSheet = "Interface";
        attribute :>> sourceRow = 386;
    }
    item trace_903b55a0b6383446 : TraceRecord {
        attribute :>> elementId = "PORT::8127::低压控制电能端口::ITM-PHY-015::双向物理";
        attribute :>> sourceFile = "Rail_MBSE_Function_Interface_v1_final.xlsx";
        attribute :>> sourceSheet = "Interface";
        attribute :>> sourceRow = 387;
    }
    item trace_be0fc7194a7f0161 : TraceRecord {
        attribute :>> elementId = "PORT::8127::安全停车_制动请求输入::ITM-CMD-030::输入";
        attribute :>> sourceFile = "Rail_MBSE_Function_Interface_v1_final.xlsx";
        attribute :>> sourceSheet = "Interface";
        attribute :>> sourceRow = 388;
    }
    item trace_8f3091a86214dd4e : TraceRecord {
        attribute :>> elementId = "PORT::8127::安全停车_制动请求输出::ITM-CMD-030::输出";
        attribute :>> sourceFile = "Rail_MBSE_Function_Interface_v1_final.xlsx";
        attribute :>> sourceSheet = "Interface";
        attribute :>> sourceRow = 389;
    }
    item trace_ce6397cb7b81dd94 : TraceRecord {
        attribute :>> elementId = "PORT::8128::ATP_外部安全系统状态输入::ITM-STA-027::输入";
        attribute :>> sourceFile = "Rail_MBSE_Function_Interface_v1_final.xlsx";
        attribute :>> sourceSheet = "Interface";
        attribute :>> sourceRow = 390;
    }
    item trace_58e3c9dfabb04a51 : TraceRecord {
        attribute :>> elementId = "PORT::8128::ATP_外部安全系统状态输出::ITM-STA-027::输出";
        attribute :>> sourceFile = "Rail_MBSE_Function_Interface_v1_final.xlsx";
        attribute :>> sourceSheet = "Interface";
        attribute :>> sourceRow = 391;
    }
    item trace_3b5ccced6e75cf2c : TraceRecord {
        attribute :>> elementId = "PORT::8128::低压控制电能端口::ITM-PHY-015::双向物理";
        attribute :>> sourceFile = "Rail_MBSE_Function_Interface_v1_final.xlsx";
        attribute :>> sourceSheet = "Interface";
        attribute :>> sourceRow = 392;
    }
    item trace_eea6ab94a057e9f5 : TraceRecord {
        attribute :>> elementId = "PORT::8128::制动安全回路状态输入::ITM-STA-025::输入";
        attribute :>> sourceFile = "Rail_MBSE_Function_Interface_v1_final.xlsx";
        attribute :>> sourceSheet = "Interface";
        attribute :>> sourceRow = 393;
    }
    item trace_9f2f985b6764bfa7 : TraceRecord {
        attribute :>> elementId = "PORT::8128::制动安全回路状态输出::ITM-STA-025::输出";
        attribute :>> sourceFile = "Rail_MBSE_Function_Interface_v1_final.xlsx";
        attribute :>> sourceSheet = "Interface";
        attribute :>> sourceRow = 394;
    }
    item trace_cc7a917501039195 : TraceRecord {
        attribute :>> elementId = "PORT::8128::制动缸压力输入::ITM-MEA-016::输入";
        attribute :>> sourceFile = "Rail_MBSE_Function_Interface_v1_final.xlsx";
        attribute :>> sourceSheet = "Interface";
        attribute :>> sourceRow = 395;
    }
    item trace_0e19632016b69ff2 : TraceRecord {
        attribute :>> elementId = "PORT::8128::制动缸压力输出::ITM-MEA-016::输出";
        attribute :>> sourceFile = "Rail_MBSE_Function_Interface_v1_final.xlsx";
        attribute :>> sourceSheet = "Interface";
        attribute :>> sourceRow = 396;
    }
    item trace_ccc90acd04ba0ccc : TraceRecord {
        attribute :>> elementId = "PORT::8128::总风管压力输入::ITM-MEA-014::输入";
        attribute :>> sourceFile = "Rail_MBSE_Function_Interface_v1_final.xlsx";
        attribute :>> sourceSheet = "Interface";
        attribute :>> sourceRow = 397;
    }
    item trace_8d19f6989a5bebad : TraceRecord {
        attribute :>> elementId = "PORT::8128::总风管压力输出::ITM-MEA-014::输出";
        attribute :>> sourceFile = "Rail_MBSE_Function_Interface_v1_final.xlsx";
        attribute :>> sourceSheet = "Interface";
        attribute :>> sourceRow = 398;
    }
    item trace_26589bfc82ed6979 : TraceRecord {
        attribute :>> elementId = "PORT::8128::撒砂请求输入::ITM-CMD-024::输入";
        attribute :>> sourceFile = "Rail_MBSE_Function_Interface_v1_final.xlsx";
        attribute :>> sourceSheet = "Interface";
        attribute :>> sourceRow = 399;
    }
    item trace_5accd69f9c3a8b0c : TraceRecord {
        attribute :>> elementId = "PORT::8128::撒砂请求输出::ITM-CMD-024::输出";
        attribute :>> sourceFile = "Rail_MBSE_Function_Interface_v1_final.xlsx";
        attribute :>> sourceSheet = "Interface";
        attribute :>> sourceRow = 400;
    }
    item trace_9819959a053f9c06 : TraceRecord {
        attribute :>> elementId = "PORT::8128::牵引安全回路状态输入::ITM-STA-026::输入";
        attribute :>> sourceFile = "Rail_MBSE_Function_Interface_v1_final.xlsx";
        attribute :>> sourceSheet = "Interface";
        attribute :>> sourceRow = 401;
    }
    item trace_aad98cbe8fa3b27e : TraceRecord {
        attribute :>> elementId = "PORT::8128::牵引安全回路状态输出::ITM-STA-026::输出";
        attribute :>> sourceFile = "Rail_MBSE_Function_Interface_v1_final.xlsx";
        attribute :>> sourceSheet = "Interface";
        attribute :>> sourceRow = 402;
    }
    item trace_ff26e108accb1302 : TraceRecord {
        attribute :>> elementId = "PORT::8128::超级电容温度输入::ITM-MEA-027::输入";
        attribute :>> sourceFile = "Rail_MBSE_Function_Interface_v1_final.xlsx";
        attribute :>> sourceSheet = "Interface";
        attribute :>> sourceRow = 403;
    }
    item trace_90dd8ed220cd5019 : TraceRecord {
        attribute :>> elementId = "PORT::8128::超级电容温度输出::ITM-MEA-027::输出";
        attribute :>> sourceFile = "Rail_MBSE_Function_Interface_v1_final.xlsx";
        attribute :>> sourceSheet = "Interface";
        attribute :>> sourceRow = 404;
    }
    item trace_51db14413b84b1f3 : TraceRecord {
        attribute :>> elementId = "PORT::8128::超级电容电压输入::ITM-MEA-025::输入";
        attribute :>> sourceFile = "Rail_MBSE_Function_Interface_v1_final.xlsx";
        attribute :>> sourceSheet = "Interface";
        attribute :>> sourceRow = 405;
    }
    item trace_69aee385a3c44822 : TraceRecord {
        attribute :>> elementId = "PORT::8128::超级电容电压输出::ITM-MEA-025::输出";
        attribute :>> sourceFile = "Rail_MBSE_Function_Interface_v1_final.xlsx";
        attribute :>> sourceSheet = "Interface";
        attribute :>> sourceRow = 406;
    }
    item trace_c50cfd567a97f3f6 : TraceRecord {
        attribute :>> elementId = "PORT::8128::超级电容电流输入::ITM-MEA-026::输入";
        attribute :>> sourceFile = "Rail_MBSE_Function_Interface_v1_final.xlsx";
        attribute :>> sourceSheet = "Interface";
        attribute :>> sourceRow = 407;
    }
    item trace_bde087e602ad92c8 : TraceRecord {
        attribute :>> elementId = "PORT::8128::超级电容电流输出::ITM-MEA-026::输出";
        attribute :>> sourceFile = "Rail_MBSE_Function_Interface_v1_final.xlsx";
        attribute :>> sourceSheet = "Interface";
        attribute :>> sourceRow = 408;
    }
    item trace_2b9604597ff0c9ac : TraceRecord {
        attribute :>> elementId = "PORT::8128::高压安全回路状态输入::ITM-STA-024::输入";
        attribute :>> sourceFile = "Rail_MBSE_Function_Interface_v1_final.xlsx";
        attribute :>> sourceSheet = "Interface";
        attribute :>> sourceRow = 409;
    }
    item trace_cb74be2d7d4a54c7 : TraceRecord {
        attribute :>> elementId = "PORT::8128::高压安全回路状态输出::ITM-STA-024::输出";
        attribute :>> sourceFile = "Rail_MBSE_Function_Interface_v1_final.xlsx";
        attribute :>> sourceSheet = "Interface";
        attribute :>> sourceRow = 410;
    }
    item trace_b128738a40d9fcd8 : TraceRecord {
        attribute :>> elementId = "PORT::8151::低压控制电能端口::ITM-PHY-015::双向物理";
        attribute :>> sourceFile = "Rail_MBSE_Function_Interface_v1_final.xlsx";
        attribute :>> sourceSheet = "Interface";
        attribute :>> sourceRow = 411;
    }
    item trace_c6902e30a0122c0e : TraceRecord {
        attribute :>> elementId = "PORT::8151::高压安全回路状态输出::ITM-STA-024::输出";
        attribute :>> sourceFile = "Rail_MBSE_Function_Interface_v1_final.xlsx";
        attribute :>> sourceSheet = "Interface";
        attribute :>> sourceRow = 412;
    }
    item trace_d7d7f4cb9554ff03 : TraceRecord {
        attribute :>> elementId = "PORT::8151::高压断路器指令输入::ITM-CMD-016::输入";
        attribute :>> sourceFile = "Rail_MBSE_Function_Interface_v1_final.xlsx";
        attribute :>> sourceSheet = "Interface";
        attribute :>> sourceRow = 413;
    }
    item trace_1e9ebcfb3cef3e9d : TraceRecord {
        attribute :>> elementId = "PORT::8152::低压控制电能端口::ITM-PHY-015::双向物理";
        attribute :>> sourceFile = "Rail_MBSE_Function_Interface_v1_final.xlsx";
        attribute :>> sourceSheet = "Interface";
        attribute :>> sourceRow = 414;
    }
    item trace_ae53feffb1e116e3 : TraceRecord {
        attribute :>> elementId = "PORT::8152::制动安全回路状态输出::ITM-STA-025::输出";
        attribute :>> sourceFile = "Rail_MBSE_Function_Interface_v1_final.xlsx";
        attribute :>> sourceSheet = "Interface";
        attribute :>> sourceRow = 415;
    }
    item trace_1e4f882572b04df5 : TraceRecord {
        attribute :>> elementId = "PORT::8152::安全停车_制动请求输入::ITM-CMD-030::输入";
        attribute :>> sourceFile = "Rail_MBSE_Function_Interface_v1_final.xlsx";
        attribute :>> sourceSheet = "Interface";
        attribute :>> sourceRow = 416;
    }
    item trace_93024c6ed1623fbd : TraceRecord {
        attribute :>> elementId = "PORT::8152::紧急制动请求输入::ITM-CMD-004::输入";
        attribute :>> sourceFile = "Rail_MBSE_Function_Interface_v1_final.xlsx";
        attribute :>> sourceSheet = "Interface";
        attribute :>> sourceRow = 417;
    }
    item trace_caee94e6ee66a74d : TraceRecord {
        attribute :>> elementId = "PORT::8154::低压控制电能端口::ITM-PHY-015::双向物理";
        attribute :>> sourceFile = "Rail_MBSE_Function_Interface_v1_final.xlsx";
        attribute :>> sourceSheet = "Interface";
        attribute :>> sourceRow = 418;
    }
    item trace_c3d327abebd9ecfd : TraceRecord {
        attribute :>> elementId = "PORT::8154::牵引使能指令输入::ITM-CMD-009::输入";
        attribute :>> sourceFile = "Rail_MBSE_Function_Interface_v1_final.xlsx";
        attribute :>> sourceSheet = "Interface";
        attribute :>> sourceRow = 419;
    }
    item trace_a8fff2340df81262 : TraceRecord {
        attribute :>> elementId = "PORT::8154::牵引切除请求输入::ITM-CMD-008::输入";
        attribute :>> sourceFile = "Rail_MBSE_Function_Interface_v1_final.xlsx";
        attribute :>> sourceSheet = "Interface";
        attribute :>> sourceRow = 420;
    }
    item trace_492d0ced994652db : TraceRecord {
        attribute :>> elementId = "PORT::8154::牵引安全回路状态输出::ITM-STA-026::输出";
        attribute :>> sourceFile = "Rail_MBSE_Function_Interface_v1_final.xlsx";
        attribute :>> sourceSheet = "Interface";
        attribute :>> sourceRow = 421;
    }
    item trace_54d624d57f57843b : TraceRecord {
        attribute :>> elementId = "PORT::8166::中间直流母线电压输入::ITM-MEA-008::输入";
        attribute :>> sourceFile = "Rail_MBSE_Function_Interface_v1_final.xlsx";
        attribute :>> sourceSheet = "Interface";
        attribute :>> sourceRow = 422;
    }
    item trace_3b0068559b0ca1e4 : TraceRecord {
        attribute :>> elementId = "PORT::8166::中间直流母线电流输入::ITM-MEA-009::输入";
        attribute :>> sourceFile = "Rail_MBSE_Function_Interface_v1_final.xlsx";
        attribute :>> sourceSheet = "Interface";
        attribute :>> sourceRow = 423;
    }
    item trace_937652db70f809a4 : TraceRecord {
        attribute :>> elementId = "PORT::8166::低压控制电能端口::ITM-PHY-015::双向物理";
        attribute :>> sourceFile = "Rail_MBSE_Function_Interface_v1_final.xlsx";
        attribute :>> sourceSheet = "Interface";
        attribute :>> sourceRow = 424;
    }
    item trace_c9c2903288a07ce0 : TraceRecord {
        attribute :>> elementId = "PORT::8166::储能吸收功率输出::ITM-ACC-004::输出";
        attribute :>> sourceFile = "Rail_MBSE_Function_Interface_v1_final.xlsx";
        attribute :>> sourceSheet = "Interface";
        attribute :>> sourceRow = 425;
    }
    item trace_99ca9a9fac8f0100 : TraceRecord {
        attribute :>> elementId = "PORT::8166::储能吸收累计能量输出::ITM-ACC-010::输出";
        attribute :>> sourceFile = "Rail_MBSE_Function_Interface_v1_final.xlsx";
        attribute :>> sourceSheet = "Interface";
        attribute :>> sourceRow = 426;
    }
    item trace_68e6377e6e18805d : TraceRecord {
        attribute :>> elementId = "PORT::8166::储能释放累计能量输出::ITM-ACC-011::输出";
        attribute :>> sourceFile = "Rail_MBSE_Function_Interface_v1_final.xlsx";
        attribute :>> sourceSheet = "Interface";
        attribute :>> sourceRow = 427;
    }
    item trace_936489b6fefaa1dd : TraceRecord {
        attribute :>> elementId = "PORT::8166::再生发电累计能量输出::ITM-ACC-008::输出";
        attribute :>> sourceFile = "Rail_MBSE_Function_Interface_v1_final.xlsx";
        attribute :>> sourceSheet = "Interface";
        attribute :>> sourceRow = 428;
    }
    item trace_7f2cae313a3e901f : TraceRecord {
        attribute :>> elementId = "PORT::8166::制动电阻耗散功率输出::ITM-ACC-005::输出";
        attribute :>> sourceFile = "Rail_MBSE_Function_Interface_v1_final.xlsx";
        attribute :>> sourceSheet = "Interface";
        attribute :>> sourceRow = 429;
    }
    item trace_468a13002030f7d1 : TraceRecord {
        attribute :>> elementId = "PORT::8166::制动电阻耗散累计能量输出::ITM-ACC-012::输出";
        attribute :>> sourceFile = "Rail_MBSE_Function_Interface_v1_final.xlsx";
        attribute :>> sourceSheet = "Interface";
        attribute :>> sourceRow = 430;
    }
    item trace_92ee631b1d7b853f : TraceRecord {
        attribute :>> elementId = "PORT::8166::可用制动能量输出::ITM-ACC-014::输出";
        attribute :>> sourceFile = "Rail_MBSE_Function_Interface_v1_final.xlsx";
        attribute :>> sourceSheet = "Interface";
        attribute :>> sourceRow = 431;
    }
    item trace_945f0734d7cfa81c : TraceRecord {
        attribute :>> elementId = "PORT::8166::回馈电网功率输出::ITM-ACC-003::输出";
        attribute :>> sourceFile = "Rail_MBSE_Function_Interface_v1_final.xlsx";
        attribute :>> sourceSheet = "Interface";
        attribute :>> sourceRow = 432;
    }
    item trace_80b4c9ee273dda42 : TraceRecord {
        attribute :>> elementId = "PORT::8166::回馈电网累计能量输出::ITM-ACC-009::输出";
        attribute :>> sourceFile = "Rail_MBSE_Function_Interface_v1_final.xlsx";
        attribute :>> sourceSheet = "Interface";
        attribute :>> sourceRow = 433;
    }
    item trace_69cd6c357d586ed9 : TraceRecord {
        attribute :>> elementId = "PORT::8166::实际再生功率输出::ITM-ACC-002::输出";
        attribute :>> sourceFile = "Rail_MBSE_Function_Interface_v1_final.xlsx";
        attribute :>> sourceSheet = "Interface";
        attribute :>> sourceRow = 434;
    }
    item trace_26114df564348068 : TraceRecord {
        attribute :>> elementId = "PORT::8166::牵引实际功率输出::ITM-ACC-001::输出";
        attribute :>> sourceFile = "Rail_MBSE_Function_Interface_v1_final.xlsx";
        attribute :>> sourceSheet = "Interface";
        attribute :>> sourceRow = 435;
    }
    item trace_f60bfecb427b2161 : TraceRecord {
        attribute :>> elementId = "PORT::8166::牵引累计能量输出::ITM-ACC-007::输出";
        attribute :>> sourceFile = "Rail_MBSE_Function_Interface_v1_final.xlsx";
        attribute :>> sourceSheet = "Interface";
        attribute :>> sourceRow = 436;
    }
    item trace_0d75944292125dac : TraceRecord {
        attribute :>> elementId = "PORT::8166::能量回收率输出::ITM-ACC-015::输出";
        attribute :>> sourceFile = "Rail_MBSE_Function_Interface_v1_final.xlsx";
        attribute :>> sourceSheet = "Interface";
        attribute :>> sourceRow = 437;
    }
    item trace_99f8b39a6442250d : TraceRecord {
        attribute :>> elementId = "PORT::8166::能量计量有效状态输出::ITM-STA-035::输出";
        attribute :>> sourceFile = "Rail_MBSE_Function_Interface_v1_final.xlsx";
        attribute :>> sourceSheet = "Interface";
        attribute :>> sourceRow = 438;
    }
    item trace_573e029523ef9946 : TraceRecord {
        attribute :>> elementId = "PORT::8166::高压线路电压输入::ITM-MEA-005::输入";
        attribute :>> sourceFile = "Rail_MBSE_Function_Interface_v1_final.xlsx";
        attribute :>> sourceSheet = "Interface";
        attribute :>> sourceRow = 439;
    }
    item trace_d9d89be1583c0e18 : TraceRecord {
        attribute :>> elementId = "PORT::8166::高压线路电流输入::ITM-MEA-006::输入";
        attribute :>> sourceFile = "Rail_MBSE_Function_Interface_v1_final.xlsx";
        attribute :>> sourceSheet = "Interface";
        attribute :>> sourceRow = 440;
    }
    item trace_8962dea15ad904c6 : TraceRecord {
        attribute :>> elementId = "PORT::D112::列车方向指令输出::ITM-CMD-001::输出";
        attribute :>> sourceFile = "Rail_MBSE_Function_Interface_v1_final.xlsx";
        attribute :>> sourceSheet = "Interface";
        attribute :>> sourceRow = 441;
    }
    item trace_9ca0d9d396f8ffd0 : TraceRecord {
        attribute :>> elementId = "PORT::D113::牵引指令输出::ITM-CMD-002::输出";
        attribute :>> sourceFile = "Rail_MBSE_Function_Interface_v1_final.xlsx";
        attribute :>> sourceSheet = "Interface";
        attribute :>> sourceRow = 442;
    }
    item trace_d3d5739989ecf2dd : TraceRecord {
        attribute :>> elementId = "PORT::D114::服务制动请求输出::ITM-CMD-003::输出";
        attribute :>> sourceFile = "Rail_MBSE_Function_Interface_v1_final.xlsx";
        attribute :>> sourceSheet = "Interface";
        attribute :>> sourceRow = 443;
    }
    item trace_d32b32814a84a88a : TraceRecord {
        attribute :>> elementId = "PORT::D121::紧急制动请求输出::ITM-CMD-004::输出";
        attribute :>> sourceFile = "Rail_MBSE_Function_Interface_v1_final.xlsx";
        attribute :>> sourceSheet = "Interface";
        attribute :>> sourceRow = 444;
    }
    item trace_9e466471f9387ad5 : TraceRecord {
        attribute :>> elementId = "PORT::D13B::撒砂请求输出::ITM-CMD-024::输出";
        attribute :>> sourceFile = "Rail_MBSE_Function_Interface_v1_final.xlsx";
        attribute :>> sourceSheet = "Interface";
        attribute :>> sourceRow = 445;
    }
    item trace_0307dc18d9537f9d : TraceRecord {
        attribute :>> elementId = "PORT::E100::ATP_外部安全系统状态输出::ITM-STA-027::输出";
        attribute :>> sourceFile = "Rail_MBSE_Function_Interface_v1_final.xlsx";
        attribute :>> sourceSheet = "Interface";
        attribute :>> sourceRow = 446;
    }
    item trace_7273a171b473f816 : TraceRecord {
        attribute :>> elementId = "PORT::E100::安全停车_制动请求输出::ITM-CMD-030::输出";
        attribute :>> sourceFile = "Rail_MBSE_Function_Interface_v1_final.xlsx";
        attribute :>> sourceSheet = "Interface";
        attribute :>> sourceRow = 447;
    }
    item trace_565c4036e651287e : TraceRecord {
        attribute :>> elementId = "PORT::X111::中间直流电能端口::ITM-PHY-003::双向物理";
        attribute :>> sourceFile = "Rail_MBSE_Function_Interface_v1_final.xlsx";
        attribute :>> sourceSheet = "Interface";
        attribute :>> sourceRow = 448;
    }
    item trace_f6cc38ed3ebf357f : TraceRecord {
        attribute :>> elementId = "PORT::X111::储能侧直流电能端口::ITM-PHY-016::双向物理";
        attribute :>> sourceFile = "Rail_MBSE_Function_Interface_v1_final.xlsx";
        attribute :>> sourceSheet = "Interface";
        attribute :>> sourceRow = 449;
    }
    item trace_3ad794182f43f4d8 : TraceRecord {
        attribute :>> elementId = "PORT::X111::储能功率请求输入::ITM-CMD-025::输入";
        attribute :>> sourceFile = "Rail_MBSE_Function_Interface_v1_final.xlsx";
        attribute :>> sourceSheet = "Interface";
        attribute :>> sourceRow = 450;
    }
    item trace_6085b3266f1baf9d : TraceRecord {
        attribute :>> elementId = "PORT::X111::双向DC_DC使能输入::ITM-CMD-026::输入";
        attribute :>> sourceFile = "Rail_MBSE_Function_Interface_v1_final.xlsx";
        attribute :>> sourceSheet = "Interface";
        attribute :>> sourceRow = 451;
    }
    item trace_9828766df3df1904 : TraceRecord {
        attribute :>> elementId = "PORT::X111::双向DC_DC实际功率输出::ITM-MEA-029::输出";
        attribute :>> sourceFile = "Rail_MBSE_Function_Interface_v1_final.xlsx";
        attribute :>> sourceSheet = "Interface";
        attribute :>> sourceRow = 452;
    }
    item trace_121334297c7e5c44 : TraceRecord {
        attribute :>> elementId = "PORT::X111::双向DC_DC故障状态输出::ITM-STA-029::输出";
        attribute :>> sourceFile = "Rail_MBSE_Function_Interface_v1_final.xlsx";
        attribute :>> sourceSheet = "Interface";
        attribute :>> sourceRow = 453;
    }
    item trace_fbc8c24ae8a5bcdd : TraceRecord {
        attribute :>> elementId = "PORT::X111::双向DC_DC状态输出::ITM-STA-028::输出";
        attribute :>> sourceFile = "Rail_MBSE_Function_Interface_v1_final.xlsx";
        attribute :>> sourceSheet = "Interface";
        attribute :>> sourceRow = 454;
    }
    item trace_74c67e7bc95576e6 : TraceRecord {
        attribute :>> elementId = "PORT::X111::双向DC_DC电流输出::ITM-MEA-030::输出";
        attribute :>> sourceFile = "Rail_MBSE_Function_Interface_v1_final.xlsx";
        attribute :>> sourceSheet = "Interface";
        attribute :>> sourceRow = 455;
    }
    item trace_89849c49127b2dfb : TraceRecord {
        attribute :>> elementId = "PORT::X112::中间直流母线电压输入::ITM-MEA-008::输入";
        attribute :>> sourceFile = "Rail_MBSE_Function_Interface_v1_final.xlsx";
        attribute :>> sourceSheet = "Interface";
        attribute :>> sourceRow = 456;
    }
    item trace_569130817376da24 : TraceRecord {
        attribute :>> elementId = "PORT::X112::低压控制电能端口::ITM-PHY-015::双向物理";
        attribute :>> sourceFile = "Rail_MBSE_Function_Interface_v1_final.xlsx";
        attribute :>> sourceSheet = "Interface";
        attribute :>> sourceRow = 457;
    }
    item trace_81f1c1da5d6d3173 : TraceRecord {
        attribute :>> elementId = "PORT::X112::储能主接触器指令输入::ITM-CMD-027::输入";
        attribute :>> sourceFile = "Rail_MBSE_Function_Interface_v1_final.xlsx";
        attribute :>> sourceSheet = "Interface";
        attribute :>> sourceRow = 458;
    }
    item trace_2ea4241545e6ca09 : TraceRecord {
        attribute :>> elementId = "PORT::X112::储能主接触器指令输出::ITM-CMD-027::输出";
        attribute :>> sourceFile = "Rail_MBSE_Function_Interface_v1_final.xlsx";
        attribute :>> sourceSheet = "Interface";
        attribute :>> sourceRow = 459;
    }
    item trace_f929a9fa6b633837 : TraceRecord {
        attribute :>> elementId = "PORT::X112::储能主接触器状态输入::ITM-STA-032::输入";
        attribute :>> sourceFile = "Rail_MBSE_Function_Interface_v1_final.xlsx";
        attribute :>> sourceSheet = "Interface";
        attribute :>> sourceRow = 460;
    }
    item trace_00da2edc928b715d : TraceRecord {
        attribute :>> elementId = "PORT::X112::储能保护跳闸状态输入::ITM-STA-034::输入";
        attribute :>> sourceFile = "Rail_MBSE_Function_Interface_v1_final.xlsx";
        attribute :>> sourceSheet = "Interface";
        attribute :>> sourceRow = 461;
    }
    item trace_843fa8c83311440e : TraceRecord {
        attribute :>> elementId = "PORT::X112::储能功率请求输入::ITM-CMD-025::输入";
        attribute :>> sourceFile = "Rail_MBSE_Function_Interface_v1_final.xlsx";
        attribute :>> sourceSheet = "Interface";
        attribute :>> sourceRow = 462;
    }
    item trace_1ca011606f062f80 : TraceRecord {
        attribute :>> elementId = "PORT::X112::储能功率请求输出::ITM-CMD-025::输出";
        attribute :>> sourceFile = "Rail_MBSE_Function_Interface_v1_final.xlsx";
        attribute :>> sourceSheet = "Interface";
        attribute :>> sourceRow = 463;
    }
    item trace_388d943a537916a7 : TraceRecord {
        attribute :>> elementId = "PORT::X112::储能可用充电功率输出::ITM-LIM-009::输出";
        attribute :>> sourceFile = "Rail_MBSE_Function_Interface_v1_final.xlsx";
        attribute :>> sourceSheet = "Interface";
        attribute :>> sourceRow = 464;
    }
    item trace_73067cce4e6a7eeb : TraceRecord {
        attribute :>> elementId = "PORT::X112::储能可用放电功率输出::ITM-LIM-010::输出";
        attribute :>> sourceFile = "Rail_MBSE_Function_Interface_v1_final.xlsx";
        attribute :>> sourceSheet = "Interface";
        attribute :>> sourceRow = 465;
    }
    item trace_a59821acb0d73604 : TraceRecord {
        attribute :>> elementId = "PORT::X112::储能吸收功率输出::ITM-ACC-004::输出";
        attribute :>> sourceFile = "Rail_MBSE_Function_Interface_v1_final.xlsx";
        attribute :>> sourceSheet = "Interface";
        attribute :>> sourceRow = 466;
    }
    item trace_b84f02a624b9982f : TraceRecord {
        attribute :>> elementId = "PORT::X112::储能故障复位指令输入::ITM-CMD-029::输入";
        attribute :>> sourceFile = "Rail_MBSE_Function_Interface_v1_final.xlsx";
        attribute :>> sourceSheet = "Interface";
        attribute :>> sourceRow = 467;
    }
    item trace_3b946767139d884a : TraceRecord {
        attribute :>> elementId = "PORT::X112::储能系统可用状态输出::ITM-STA-030::输出";
        attribute :>> sourceFile = "Rail_MBSE_Function_Interface_v1_final.xlsx";
        attribute :>> sourceSheet = "Interface";
        attribute :>> sourceRow = 468;
    }
    item trace_e5eadfefaf46ac0a : TraceRecord {
        attribute :>> elementId = "PORT::X112::储能系统故障状态输出::ITM-STA-031::输出";
        attribute :>> sourceFile = "Rail_MBSE_Function_Interface_v1_final.xlsx";
        attribute :>> sourceSheet = "Interface";
        attribute :>> sourceRow = 469;
    }
    item trace_5ff890136d5d49bf : TraceRecord {
        attribute :>> elementId = "PORT::X112::储能预充电指令输入::ITM-CMD-028::输入";
        attribute :>> sourceFile = "Rail_MBSE_Function_Interface_v1_final.xlsx";
        attribute :>> sourceSheet = "Interface";
        attribute :>> sourceRow = 470;
    }
    item trace_adb78cdbb75469df : TraceRecord {
        attribute :>> elementId = "PORT::X112::储能预充电指令输出::ITM-CMD-028::输出";
        attribute :>> sourceFile = "Rail_MBSE_Function_Interface_v1_final.xlsx";
        attribute :>> sourceSheet = "Interface";
        attribute :>> sourceRow = 471;
    }
    item trace_3ecd9966c9972a7e : TraceRecord {
        attribute :>> elementId = "PORT::X112::储能预充电状态输入::ITM-STA-033::输入";
        attribute :>> sourceFile = "Rail_MBSE_Function_Interface_v1_final.xlsx";
        attribute :>> sourceSheet = "Interface";
        attribute :>> sourceRow = 472;
    }
    item trace_1164249ec859b807 : TraceRecord {
        attribute :>> elementId = "PORT::X112::双向DC_DC使能输入::ITM-CMD-026::输入";
        attribute :>> sourceFile = "Rail_MBSE_Function_Interface_v1_final.xlsx";
        attribute :>> sourceSheet = "Interface";
        attribute :>> sourceRow = 473;
    }
    item trace_f980a38f780089b6 : TraceRecord {
        attribute :>> elementId = "PORT::X112::双向DC_DC使能输出::ITM-CMD-026::输出";
        attribute :>> sourceFile = "Rail_MBSE_Function_Interface_v1_final.xlsx";
        attribute :>> sourceSheet = "Interface";
        attribute :>> sourceRow = 474;
    }
    item trace_4659cbe7e3b50b58 : TraceRecord {
        attribute :>> elementId = "PORT::X112::双向DC_DC实际功率输入::ITM-MEA-029::输入";
        attribute :>> sourceFile = "Rail_MBSE_Function_Interface_v1_final.xlsx";
        attribute :>> sourceSheet = "Interface";
        attribute :>> sourceRow = 475;
    }
    item trace_d8c491383c9a24dc : TraceRecord {
        attribute :>> elementId = "PORT::X112::双向DC_DC故障状态输出::ITM-STA-029::输出";
        attribute :>> sourceFile = "Rail_MBSE_Function_Interface_v1_final.xlsx";
        attribute :>> sourceSheet = "Interface";
        attribute :>> sourceRow = 476;
    }
    item trace_96349f1cf75b3d94 : TraceRecord {
        attribute :>> elementId = "PORT::X112::双向DC_DC状态输出::ITM-STA-028::输出";
        attribute :>> sourceFile = "Rail_MBSE_Function_Interface_v1_final.xlsx";
        attribute :>> sourceSheet = "Interface";
        attribute :>> sourceRow = 477;
    }
    item trace_88bb7293920adfa8 : TraceRecord {
        attribute :>> elementId = "PORT::X112::双向DC_DC电流输入::ITM-MEA-030::输入";
        attribute :>> sourceFile = "Rail_MBSE_Function_Interface_v1_final.xlsx";
        attribute :>> sourceSheet = "Interface";
        attribute :>> sourceRow = 478;
    }
    item trace_1f01277587ee6905 : TraceRecord {
        attribute :>> elementId = "PORT::X112::直流母线电压上限输入::ITM-LIM-007::输入";
        attribute :>> sourceFile = "Rail_MBSE_Function_Interface_v1_final.xlsx";
        attribute :>> sourceSheet = "Interface";
        attribute :>> sourceRow = 479;
    }
    item trace_ced58e17348ff578 : TraceRecord {
        attribute :>> elementId = "PORT::X112::超级电容SOC输入::ITM-MEA-028::输入";
        attribute :>> sourceFile = "Rail_MBSE_Function_Interface_v1_final.xlsx";
        attribute :>> sourceSheet = "Interface";
        attribute :>> sourceRow = 480;
    }
    item trace_0dcfac1fe8bbd763 : TraceRecord {
        attribute :>> elementId = "PORT::X112::超级电容充电允许状态输出::ITM-LIM-011::输出";
        attribute :>> sourceFile = "Rail_MBSE_Function_Interface_v1_final.xlsx";
        attribute :>> sourceSheet = "Interface";
        attribute :>> sourceRow = 481;
    }
    item trace_651a62a644935ccb : TraceRecord {
        attribute :>> elementId = "PORT::X112::超级电容放电允许状态输出::ITM-LIM-012::输出";
        attribute :>> sourceFile = "Rail_MBSE_Function_Interface_v1_final.xlsx";
        attribute :>> sourceSheet = "Interface";
        attribute :>> sourceRow = 482;
    }
    item trace_848f140649f8e2ae : TraceRecord {
        attribute :>> elementId = "PORT::X112::超级电容温度输入::ITM-MEA-027::输入";
        attribute :>> sourceFile = "Rail_MBSE_Function_Interface_v1_final.xlsx";
        attribute :>> sourceSheet = "Interface";
        attribute :>> sourceRow = 483;
    }
    item trace_fc5798a77b6a020d : TraceRecord {
        attribute :>> elementId = "PORT::X112::超级电容电压输入::ITM-MEA-025::输入";
        attribute :>> sourceFile = "Rail_MBSE_Function_Interface_v1_final.xlsx";
        attribute :>> sourceSheet = "Interface";
        attribute :>> sourceRow = 484;
    }
    item trace_e8341f592e73af5e : TraceRecord {
        attribute :>> elementId = "PORT::X112::超级电容电流输入::ITM-MEA-026::输入";
        attribute :>> sourceFile = "Rail_MBSE_Function_Interface_v1_final.xlsx";
        attribute :>> sourceSheet = "Interface";
        attribute :>> sourceRow = 485;
    }
    item trace_0e45c7ab357a42e6 : TraceRecord {
        attribute :>> elementId = "PORT::X113::中间直流母线电压输出::ITM-MEA-008::输出";
        attribute :>> sourceFile = "Rail_MBSE_Function_Interface_v1_final.xlsx";
        attribute :>> sourceSheet = "Interface";
        attribute :>> sourceRow = 486;
    }
    item trace_571e6f079e1116ac : TraceRecord {
        attribute :>> elementId = "PORT::X113::中间直流电能端口::ITM-PHY-003::双向物理";
        attribute :>> sourceFile = "Rail_MBSE_Function_Interface_v1_final.xlsx";
        attribute :>> sourceSheet = "Interface";
        attribute :>> sourceRow = 487;
    }
    item trace_9f0c62635f9ae105 : TraceRecord {
        attribute :>> elementId = "PORT::X113::低压控制电能端口::ITM-PHY-015::双向物理";
        attribute :>> sourceFile = "Rail_MBSE_Function_Interface_v1_final.xlsx";
        attribute :>> sourceSheet = "Interface";
        attribute :>> sourceRow = 488;
    }
    item trace_5e8b7419342ecb12 : TraceRecord {
        attribute :>> elementId = "PORT::X113::储能侧直流电能端口::ITM-PHY-016::双向物理";
        attribute :>> sourceFile = "Rail_MBSE_Function_Interface_v1_final.xlsx";
        attribute :>> sourceSheet = "Interface";
        attribute :>> sourceRow = 489;
    }
    item trace_fdb7d950b1296be2 : TraceRecord {
        attribute :>> elementId = "PORT::X113::储能保护跳闸状态输出::ITM-STA-034::输出";
        attribute :>> sourceFile = "Rail_MBSE_Function_Interface_v1_final.xlsx";
        attribute :>> sourceSheet = "Interface";
        attribute :>> sourceRow = 490;
    }
    item trace_bbb42fe7ea40668f : TraceRecord {
        attribute :>> elementId = "PORT::X113::储能可用充电功率输出::ITM-LIM-009::输出";
        attribute :>> sourceFile = "Rail_MBSE_Function_Interface_v1_final.xlsx";
        attribute :>> sourceSheet = "Interface";
        attribute :>> sourceRow = 491;
    }
    item trace_1a2f8620b785c434 : TraceRecord {
        attribute :>> elementId = "PORT::X113::储能可用放电功率输出::ITM-LIM-010::输出";
        attribute :>> sourceFile = "Rail_MBSE_Function_Interface_v1_final.xlsx";
        attribute :>> sourceSheet = "Interface";
        attribute :>> sourceRow = 492;
    }
    item trace_b96276443bd011b6 : TraceRecord {
        attribute :>> elementId = "PORT::X113::储能系统故障状态输出::ITM-STA-031::输出";
        attribute :>> sourceFile = "Rail_MBSE_Function_Interface_v1_final.xlsx";
        attribute :>> sourceSheet = "Interface";
        attribute :>> sourceRow = 493;
    }
    item trace_97ac296a7909b915 : TraceRecord {
        attribute :>> elementId = "PORT::X113::双向DC_DC故障状态输出::ITM-STA-029::输出";
        attribute :>> sourceFile = "Rail_MBSE_Function_Interface_v1_final.xlsx";
        attribute :>> sourceSheet = "Interface";
        attribute :>> sourceRow = 494;
    }
    item trace_30a4f2a71d158c56 : TraceRecord {
        attribute :>> elementId = "PORT::X113::双向DC_DC电流输出::ITM-MEA-030::输出";
        attribute :>> sourceFile = "Rail_MBSE_Function_Interface_v1_final.xlsx";
        attribute :>> sourceSheet = "Interface";
        attribute :>> sourceRow = 495;
    }
    item trace_d9c32040ebe6917e : TraceRecord {
        attribute :>> elementId = "PORT::X113::直流母线电压上限输出::ITM-LIM-007::输出";
        attribute :>> sourceFile = "Rail_MBSE_Function_Interface_v1_final.xlsx";
        attribute :>> sourceSheet = "Interface";
        attribute :>> sourceRow = 496;
    }
    item trace_180c13c086da3d55 : TraceRecord {
        attribute :>> elementId = "PORT::X113::超级电容温度输出::ITM-MEA-027::输出";
        attribute :>> sourceFile = "Rail_MBSE_Function_Interface_v1_final.xlsx";
        attribute :>> sourceSheet = "Interface";
        attribute :>> sourceRow = 497;
    }
    item trace_5926a6f58d47dc95 : TraceRecord {
        attribute :>> elementId = "PORT::X113::超级电容电压输出::ITM-MEA-025::输出";
        attribute :>> sourceFile = "Rail_MBSE_Function_Interface_v1_final.xlsx";
        attribute :>> sourceSheet = "Interface";
        attribute :>> sourceRow = 498;
    }
    item trace_2f7c47b1b3242c83 : TraceRecord {
        attribute :>> elementId = "PORT::X113::超级电容电流输出::ITM-MEA-026::输出";
        attribute :>> sourceFile = "Rail_MBSE_Function_Interface_v1_final.xlsx";
        attribute :>> sourceSheet = "Interface";
        attribute :>> sourceRow = 499;
    }
    item trace_e7b0b50420861015 : TraceRecord {
        attribute :>> elementId = "PORT::X121::储能侧直流电能端口::ITM-PHY-016::双向物理";
        attribute :>> sourceFile = "Rail_MBSE_Function_Interface_v1_final.xlsx";
        attribute :>> sourceSheet = "Interface";
        attribute :>> sourceRow = 500;
    }
    item trace_387cdae1b4483182 : TraceRecord {
        attribute :>> elementId = "PORT::X121::热能_热流端口::ITM-PHY-013::双向物理";
        attribute :>> sourceFile = "Rail_MBSE_Function_Interface_v1_final.xlsx";
        attribute :>> sourceSheet = "Interface";
        attribute :>> sourceRow = 501;
    }
    item trace_b6cf5a49ced52abf : TraceRecord {
        attribute :>> elementId = "PORT::X121::超级电容SOC输出::ITM-MEA-028::输出";
        attribute :>> sourceFile = "Rail_MBSE_Function_Interface_v1_final.xlsx";
        attribute :>> sourceSheet = "Interface";
        attribute :>> sourceRow = 502;
    }
    item trace_0b3c69b37f8b252c : TraceRecord {
        attribute :>> elementId = "PORT::X122::储能侧直流电能端口::ITM-PHY-016::双向物理";
        attribute :>> sourceFile = "Rail_MBSE_Function_Interface_v1_final.xlsx";
        attribute :>> sourceSheet = "Interface";
        attribute :>> sourceRow = 503;
    }
    item trace_370359531bcbeddd : TraceRecord {
        attribute :>> elementId = "PORT::X122::超级电容电压输出::ITM-MEA-025::输出";
        attribute :>> sourceFile = "Rail_MBSE_Function_Interface_v1_final.xlsx";
        attribute :>> sourceSheet = "Interface";
        attribute :>> sourceRow = 504;
    }
    item trace_b6c8109cae13eea5 : TraceRecord {
        attribute :>> elementId = "PORT::X123::储能侧直流电能端口::ITM-PHY-016::双向物理";
        attribute :>> sourceFile = "Rail_MBSE_Function_Interface_v1_final.xlsx";
        attribute :>> sourceSheet = "Interface";
        attribute :>> sourceRow = 505;
    }
    item trace_9b6812b4ca482c66 : TraceRecord {
        attribute :>> elementId = "PORT::X123::超级电容电流输出::ITM-MEA-026::输出";
        attribute :>> sourceFile = "Rail_MBSE_Function_Interface_v1_final.xlsx";
        attribute :>> sourceSheet = "Interface";
        attribute :>> sourceRow = 506;
    }
    item trace_5083db510ca305a5 : TraceRecord {
        attribute :>> elementId = "PORT::X124::超级电容温度输出::ITM-MEA-027::输出";
        attribute :>> sourceFile = "Rail_MBSE_Function_Interface_v1_final.xlsx";
        attribute :>> sourceSheet = "Interface";
        attribute :>> sourceRow = 507;
    }
    item trace_4d5eafc70549d9c0 : TraceRecord {
        attribute :>> elementId = "PORT::X124::超级电容热能感知端口::ITM-PHY-013::双向物理";
        attribute :>> sourceFile = "Rail_MBSE_Function_Interface_v1_final.xlsx";
        attribute :>> sourceSheet = "Interface";
        attribute :>> sourceRow = 508;
    }
    item trace_b06975e1baff62be : TraceRecord {
        attribute :>> elementId = "PORT::X131::储能主接触器指令输入::ITM-CMD-027::输入";
        attribute :>> sourceFile = "Rail_MBSE_Function_Interface_v1_final.xlsx";
        attribute :>> sourceSheet = "Interface";
        attribute :>> sourceRow = 509;
    }
    item trace_c029b3b1472e957d : TraceRecord {
        attribute :>> elementId = "PORT::X131::储能主接触器状态输出::ITM-STA-032::输出";
        attribute :>> sourceFile = "Rail_MBSE_Function_Interface_v1_final.xlsx";
        attribute :>> sourceSheet = "Interface";
        attribute :>> sourceRow = 510;
    }
    item trace_ef3e7082da0c5648 : TraceRecord {
        attribute :>> elementId = "PORT::X131::母线段储能侧直流电能端口::ITM-PHY-016::双向物理";
        attribute :>> sourceFile = "Rail_MBSE_Function_Interface_v1_final.xlsx";
        attribute :>> sourceSheet = "Interface";
        attribute :>> sourceRow = 511;
    }
    item trace_6bdc28fa4761142d : TraceRecord {
        attribute :>> elementId = "PORT::X131::负载段储能侧直流电能端口::ITM-PHY-016::双向物理";
        attribute :>> sourceFile = "Rail_MBSE_Function_Interface_v1_final.xlsx";
        attribute :>> sourceSheet = "Interface";
        attribute :>> sourceRow = 512;
    }
    item trace_4d68d3f9ee4e0009 : TraceRecord {
        attribute :>> elementId = "PORT::X132::储能预充电指令输入::ITM-CMD-028::输入";
        attribute :>> sourceFile = "Rail_MBSE_Function_Interface_v1_final.xlsx";
        attribute :>> sourceSheet = "Interface";
        attribute :>> sourceRow = 513;
    }
    item trace_53191daa39f85d49 : TraceRecord {
        attribute :>> elementId = "PORT::X132::储能预充电状态输出::ITM-STA-033::输出";
        attribute :>> sourceFile = "Rail_MBSE_Function_Interface_v1_final.xlsx";
        attribute :>> sourceSheet = "Interface";
        attribute :>> sourceRow = 514;
    }
    item trace_0fa709507856ec0b : TraceRecord {
        attribute :>> elementId = "PORT::X132::预充输入段储能侧直流电能端口::ITM-PHY-016::双向物理";
        attribute :>> sourceFile = "Rail_MBSE_Function_Interface_v1_final.xlsx";
        attribute :>> sourceSheet = "Interface";
        attribute :>> sourceRow = 515;
    }
    item trace_1d9e411fc4e0ebf9 : TraceRecord {
        attribute :>> elementId = "PORT::X132::预充输出段储能侧直流电能端口::ITM-PHY-016::双向物理";
        attribute :>> sourceFile = "Rail_MBSE_Function_Interface_v1_final.xlsx";
        attribute :>> sourceSheet = "Interface";
        attribute :>> sourceRow = 516;
    }
    item trace_da93423081013940 : TraceRecord {
        attribute :>> elementId = "PORT::X133::低压控制电能端口::ITM-PHY-015::双向物理";
        attribute :>> sourceFile = "Rail_MBSE_Function_Interface_v1_final.xlsx";
        attribute :>> sourceSheet = "Interface";
        attribute :>> sourceRow = 517;
    }
    item trace_06282bbd1af76861 : TraceRecord {
        attribute :>> elementId = "PORT::X133::保护输入段储能侧直流电能端口::ITM-PHY-016::双向物理";
        attribute :>> sourceFile = "Rail_MBSE_Function_Interface_v1_final.xlsx";
        attribute :>> sourceSheet = "Interface";
        attribute :>> sourceRow = 518;
    }
    item trace_49a2b1a2497ebf63 : TraceRecord {
        attribute :>> elementId = "PORT::X133::保护输出段储能侧直流电能端口::ITM-PHY-016::双向物理";
        attribute :>> sourceFile = "Rail_MBSE_Function_Interface_v1_final.xlsx";
        attribute :>> sourceSheet = "Interface";
        attribute :>> sourceRow = 519;
    }
    item trace_ffcdb33099ab8a28 : TraceRecord {
        attribute :>> elementId = "PORT::X133::储能保护跳闸状态输出::ITM-STA-034::输出";
        attribute :>> sourceFile = "Rail_MBSE_Function_Interface_v1_final.xlsx";
        attribute :>> sourceSheet = "Interface";
        attribute :>> sourceRow = 520;
    }
    item trace_0ac161b92c0e41a0 : TraceRecord {
        attribute :>> elementId = "PORT::X133::储能系统故障状态输出::ITM-STA-031::输出";
        attribute :>> sourceFile = "Rail_MBSE_Function_Interface_v1_final.xlsx";
        attribute :>> sourceSheet = "Interface";
        attribute :>> sourceRow = 521;
    }
    item trace_180ae31df40896e6 : TraceRecord {
        attribute :>> elementId = "F-3000-01";
        attribute :>> sourceFile = "Rail_MBSE_Function_Interface_v1_final.xlsx";
        attribute :>> sourceSheet = "Function";
        attribute :>> sourceRow = 5;
    }
    item trace_18cb71ec61348460 : TraceRecord {
        attribute :>> elementId = "F-3100-01";
        attribute :>> sourceFile = "Rail_MBSE_Function_Interface_v1_final.xlsx";
        attribute :>> sourceSheet = "Function";
        attribute :>> sourceRow = 6;
    }
    item trace_880e67072c4f8949 : TraceRecord {
        attribute :>> elementId = "F-3110-01";
        attribute :>> sourceFile = "Rail_MBSE_Function_Interface_v1_final.xlsx";
        attribute :>> sourceSheet = "Function";
        attribute :>> sourceRow = 7;
    }
    item trace_983e4dc2e1b70e5f : TraceRecord {
        attribute :>> elementId = "F-3111-01";
        attribute :>> sourceFile = "Rail_MBSE_Function_Interface_v1_final.xlsx";
        attribute :>> sourceSheet = "Function";
        attribute :>> sourceRow = 8;
    }
    item trace_07a717b261a598f5 : TraceRecord {
        attribute :>> elementId = "F-3112-01";
        attribute :>> sourceFile = "Rail_MBSE_Function_Interface_v1_final.xlsx";
        attribute :>> sourceSheet = "Function";
        attribute :>> sourceRow = 9;
    }
    item trace_31ab8ce4ea89f169 : TraceRecord {
        attribute :>> elementId = "F-3120-01";
        attribute :>> sourceFile = "Rail_MBSE_Function_Interface_v1_final.xlsx";
        attribute :>> sourceSheet = "Function";
        attribute :>> sourceRow = 10;
    }
    item trace_1787ba1468a6e958 : TraceRecord {
        attribute :>> elementId = "F-3121-01";
        attribute :>> sourceFile = "Rail_MBSE_Function_Interface_v1_final.xlsx";
        attribute :>> sourceSheet = "Function";
        attribute :>> sourceRow = 11;
    }
    item trace_a28774918edbfc99 : TraceRecord {
        attribute :>> elementId = "F-3130-01";
        attribute :>> sourceFile = "Rail_MBSE_Function_Interface_v1_final.xlsx";
        attribute :>> sourceSheet = "Function";
        attribute :>> sourceRow = 12;
    }
    item trace_1e0557b0f773ea34 : TraceRecord {
        attribute :>> elementId = "F-3131-01";
        attribute :>> sourceFile = "Rail_MBSE_Function_Interface_v1_final.xlsx";
        attribute :>> sourceSheet = "Function";
        attribute :>> sourceRow = 13;
    }
    item trace_c774c79b0914b24c : TraceRecord {
        attribute :>> elementId = "F-3132-01";
        attribute :>> sourceFile = "Rail_MBSE_Function_Interface_v1_final.xlsx";
        attribute :>> sourceSheet = "Function";
        attribute :>> sourceRow = 14;
    }
    item trace_84b08e2ce6e50f12 : TraceRecord {
        attribute :>> elementId = "F-3133-01";
        attribute :>> sourceFile = "Rail_MBSE_Function_Interface_v1_final.xlsx";
        attribute :>> sourceSheet = "Function";
        attribute :>> sourceRow = 15;
    }
    item trace_06bab490647c4098 : TraceRecord {
        attribute :>> elementId = "F-3500-01";
        attribute :>> sourceFile = "Rail_MBSE_Function_Interface_v1_final.xlsx";
        attribute :>> sourceSheet = "Function";
        attribute :>> sourceRow = 16;
    }
    item trace_5b768064bafd99b8 : TraceRecord {
        attribute :>> elementId = "F-3510-01";
        attribute :>> sourceFile = "Rail_MBSE_Function_Interface_v1_final.xlsx";
        attribute :>> sourceSheet = "Function";
        attribute :>> sourceRow = 17;
    }
    item trace_26ac2fc63e6b6fbb : TraceRecord {
        attribute :>> elementId = "F-3511-01";
        attribute :>> sourceFile = "Rail_MBSE_Function_Interface_v1_final.xlsx";
        attribute :>> sourceSheet = "Function";
        attribute :>> sourceRow = 18;
    }
    item trace_f443c053cdced738 : TraceRecord {
        attribute :>> elementId = "F-3512-01";
        attribute :>> sourceFile = "Rail_MBSE_Function_Interface_v1_final.xlsx";
        attribute :>> sourceSheet = "Function";
        attribute :>> sourceRow = 19;
    }
    item trace_35110d13dd13e38a : TraceRecord {
        attribute :>> elementId = "F-3514-01";
        attribute :>> sourceFile = "Rail_MBSE_Function_Interface_v1_final.xlsx";
        attribute :>> sourceSheet = "Function";
        attribute :>> sourceRow = 20;
    }
    item trace_a54ece21555c24a5 : TraceRecord {
        attribute :>> elementId = "F-3600-01";
        attribute :>> sourceFile = "Rail_MBSE_Function_Interface_v1_final.xlsx";
        attribute :>> sourceSheet = "Function";
        attribute :>> sourceRow = 21;
    }
    item trace_c12a718abfacb92d : TraceRecord {
        attribute :>> elementId = "F-3640-01";
        attribute :>> sourceFile = "Rail_MBSE_Function_Interface_v1_final.xlsx";
        attribute :>> sourceSheet = "Function";
        attribute :>> sourceRow = 22;
    }
    item trace_327b767d3895a2e3 : TraceRecord {
        attribute :>> elementId = "F-3641-01";
        attribute :>> sourceFile = "Rail_MBSE_Function_Interface_v1_final.xlsx";
        attribute :>> sourceSheet = "Function";
        attribute :>> sourceRow = 23;
    }
    item trace_514840513c79a154 : TraceRecord {
        attribute :>> elementId = "F-3643-01";
        attribute :>> sourceFile = "Rail_MBSE_Function_Interface_v1_final.xlsx";
        attribute :>> sourceSheet = "Function";
        attribute :>> sourceRow = 24;
    }
    item trace_1a47f45acc2f0d2c : TraceRecord {
        attribute :>> elementId = "F-3644-01";
        attribute :>> sourceFile = "Rail_MBSE_Function_Interface_v1_final.xlsx";
        attribute :>> sourceSheet = "Function";
        attribute :>> sourceRow = 25;
    }
    item trace_d2d6ed71b441db56 : TraceRecord {
        attribute :>> elementId = "F-3800-01";
        attribute :>> sourceFile = "Rail_MBSE_Function_Interface_v1_final.xlsx";
        attribute :>> sourceSheet = "Function";
        attribute :>> sourceRow = 26;
    }
    item trace_6ef387f2a88bbe34 : TraceRecord {
        attribute :>> elementId = "F-3810-01";
        attribute :>> sourceFile = "Rail_MBSE_Function_Interface_v1_final.xlsx";
        attribute :>> sourceSheet = "Function";
        attribute :>> sourceRow = 27;
    }
    item trace_cc0829ae32483e0f : TraceRecord {
        attribute :>> elementId = "F-3811-01";
        attribute :>> sourceFile = "Rail_MBSE_Function_Interface_v1_final.xlsx";
        attribute :>> sourceSheet = "Function";
        attribute :>> sourceRow = 28;
    }
    item trace_b1e1b7115d497840 : TraceRecord {
        attribute :>> elementId = "F-3811-02";
        attribute :>> sourceFile = "Rail_MBSE_Function_Interface_v1_final.xlsx";
        attribute :>> sourceSheet = "Function";
        attribute :>> sourceRow = 29;
    }
    item trace_5c0a07d726edf9e7 : TraceRecord {
        attribute :>> elementId = "F-3813-01";
        attribute :>> sourceFile = "Rail_MBSE_Function_Interface_v1_final.xlsx";
        attribute :>> sourceSheet = "Function";
        attribute :>> sourceRow = 30;
    }
    item trace_7c794c9304d36f3d : TraceRecord {
        attribute :>> elementId = "F-3814-01";
        attribute :>> sourceFile = "Rail_MBSE_Function_Interface_v1_final.xlsx";
        attribute :>> sourceSheet = "Function";
        attribute :>> sourceRow = 31;
    }
    item trace_d4782efe1d0810bf : TraceRecord {
        attribute :>> elementId = "F-4000-01";
        attribute :>> sourceFile = "Rail_MBSE_Function_Interface_v1_final.xlsx";
        attribute :>> sourceSheet = "Function";
        attribute :>> sourceRow = 32;
    }
    item trace_57718346f829822e : TraceRecord {
        attribute :>> elementId = "F-4100-01";
        attribute :>> sourceFile = "Rail_MBSE_Function_Interface_v1_final.xlsx";
        attribute :>> sourceSheet = "Function";
        attribute :>> sourceRow = 33;
    }
    item trace_7e1a204b5c5a15e2 : TraceRecord {
        attribute :>> elementId = "F-4110-01";
        attribute :>> sourceFile = "Rail_MBSE_Function_Interface_v1_final.xlsx";
        attribute :>> sourceSheet = "Function";
        attribute :>> sourceRow = 34;
    }
    item trace_fb5ba3b09fdc8e51 : TraceRecord {
        attribute :>> elementId = "F-4111-01";
        attribute :>> sourceFile = "Rail_MBSE_Function_Interface_v1_final.xlsx";
        attribute :>> sourceSheet = "Function";
        attribute :>> sourceRow = 35;
    }
    item trace_aa425c40793d5f8d : TraceRecord {
        attribute :>> elementId = "F-411C-01";
        attribute :>> sourceFile = "Rail_MBSE_Function_Interface_v1_final.xlsx";
        attribute :>> sourceSheet = "Function";
        attribute :>> sourceRow = 36;
    }
    item trace_d7fe457516445e19 : TraceRecord {
        attribute :>> elementId = "F-411C-02";
        attribute :>> sourceFile = "Rail_MBSE_Function_Interface_v1_final.xlsx";
        attribute :>> sourceSheet = "Function";
        attribute :>> sourceRow = 37;
    }
    item trace_df29a11427875aa1 : TraceRecord {
        attribute :>> elementId = "F-4200-01";
        attribute :>> sourceFile = "Rail_MBSE_Function_Interface_v1_final.xlsx";
        attribute :>> sourceSheet = "Function";
        attribute :>> sourceRow = 38;
    }
    item trace_9fa447b3dff31ef4 : TraceRecord {
        attribute :>> elementId = "F-4210-01";
        attribute :>> sourceFile = "Rail_MBSE_Function_Interface_v1_final.xlsx";
        attribute :>> sourceSheet = "Function";
        attribute :>> sourceRow = 39;
    }
    item trace_eb889a7e4a4ac49f : TraceRecord {
        attribute :>> elementId = "F-4211-01";
        attribute :>> sourceFile = "Rail_MBSE_Function_Interface_v1_final.xlsx";
        attribute :>> sourceSheet = "Function";
        attribute :>> sourceRow = 40;
    }
    item trace_bd2592a4f241558d : TraceRecord {
        attribute :>> elementId = "F-4212-01";
        attribute :>> sourceFile = "Rail_MBSE_Function_Interface_v1_final.xlsx";
        attribute :>> sourceSheet = "Function";
        attribute :>> sourceRow = 41;
    }
    item trace_18f81a7c2c1ed7f5 : TraceRecord {
        attribute :>> elementId = "F-4230-01";
        attribute :>> sourceFile = "Rail_MBSE_Function_Interface_v1_final.xlsx";
        attribute :>> sourceSheet = "Function";
        attribute :>> sourceRow = 42;
    }
    item trace_bec40d54ca055d92 : TraceRecord {
        attribute :>> elementId = "F-4235-01";
        attribute :>> sourceFile = "Rail_MBSE_Function_Interface_v1_final.xlsx";
        attribute :>> sourceSheet = "Function";
        attribute :>> sourceRow = 43;
    }
    item trace_51020b5c248737f9 : TraceRecord {
        attribute :>> elementId = "F-4236-01";
        attribute :>> sourceFile = "Rail_MBSE_Function_Interface_v1_final.xlsx";
        attribute :>> sourceSheet = "Function";
        attribute :>> sourceRow = 44;
    }
    item trace_2ac0102cbbb4c3b2 : TraceRecord {
        attribute :>> elementId = "F-4238-01";
        attribute :>> sourceFile = "Rail_MBSE_Function_Interface_v1_final.xlsx";
        attribute :>> sourceSheet = "Function";
        attribute :>> sourceRow = 45;
    }
    item trace_6ba924ff2a79aa36 : TraceRecord {
        attribute :>> elementId = "F-4238-02";
        attribute :>> sourceFile = "Rail_MBSE_Function_Interface_v1_final.xlsx";
        attribute :>> sourceSheet = "Function";
        attribute :>> sourceRow = 46;
    }
    item trace_f946c5aba4673646 : TraceRecord {
        attribute :>> elementId = "F-4238-03";
        attribute :>> sourceFile = "Rail_MBSE_Function_Interface_v1_final.xlsx";
        attribute :>> sourceSheet = "Function";
        attribute :>> sourceRow = 47;
    }
    item trace_a12eb4c2afc42e8f : TraceRecord {
        attribute :>> elementId = "F-4239-01";
        attribute :>> sourceFile = "Rail_MBSE_Function_Interface_v1_final.xlsx";
        attribute :>> sourceSheet = "Function";
        attribute :>> sourceRow = 48;
    }
    item trace_425a0dde795d053e : TraceRecord {
        attribute :>> elementId = "F-4239-02";
        attribute :>> sourceFile = "Rail_MBSE_Function_Interface_v1_final.xlsx";
        attribute :>> sourceSheet = "Function";
        attribute :>> sourceRow = 49;
    }
    item trace_629a40ca08ebcd87 : TraceRecord {
        attribute :>> elementId = "F-4239-03";
        attribute :>> sourceFile = "Rail_MBSE_Function_Interface_v1_final.xlsx";
        attribute :>> sourceSheet = "Function";
        attribute :>> sourceRow = 50;
    }
    item trace_a29521f0ce6833a6 : TraceRecord {
        attribute :>> elementId = "F-4240-01";
        attribute :>> sourceFile = "Rail_MBSE_Function_Interface_v1_final.xlsx";
        attribute :>> sourceSheet = "Function";
        attribute :>> sourceRow = 51;
    }
    item trace_a9897b6bdeaa8694 : TraceRecord {
        attribute :>> elementId = "F-4241-01";
        attribute :>> sourceFile = "Rail_MBSE_Function_Interface_v1_final.xlsx";
        attribute :>> sourceSheet = "Function";
        attribute :>> sourceRow = 52;
    }
    item trace_b1481d976efda445 : TraceRecord {
        attribute :>> elementId = "F-4241-02";
        attribute :>> sourceFile = "Rail_MBSE_Function_Interface_v1_final.xlsx";
        attribute :>> sourceSheet = "Function";
        attribute :>> sourceRow = 53;
    }
    item trace_547e7e845617a975 : TraceRecord {
        attribute :>> elementId = "F-4241-03";
        attribute :>> sourceFile = "Rail_MBSE_Function_Interface_v1_final.xlsx";
        attribute :>> sourceSheet = "Function";
        attribute :>> sourceRow = 54;
    }
    item trace_51e856fb53bad775 : TraceRecord {
        attribute :>> elementId = "F-4400-01";
        attribute :>> sourceFile = "Rail_MBSE_Function_Interface_v1_final.xlsx";
        attribute :>> sourceSheet = "Function";
        attribute :>> sourceRow = 55;
    }
    item trace_80f826dc84d65390 : TraceRecord {
        attribute :>> elementId = "F-4410-01";
        attribute :>> sourceFile = "Rail_MBSE_Function_Interface_v1_final.xlsx";
        attribute :>> sourceSheet = "Function";
        attribute :>> sourceRow = 56;
    }
    item trace_9783db00d42846e4 : TraceRecord {
        attribute :>> elementId = "F-4411-01";
        attribute :>> sourceFile = "Rail_MBSE_Function_Interface_v1_final.xlsx";
        attribute :>> sourceSheet = "Function";
        attribute :>> sourceRow = 57;
    }
    item trace_5803e14ccfd9a94c : TraceRecord {
        attribute :>> elementId = "F-4412-01";
        attribute :>> sourceFile = "Rail_MBSE_Function_Interface_v1_final.xlsx";
        attribute :>> sourceSheet = "Function";
        attribute :>> sourceRow = 58;
    }
    item trace_090dea8a86835b9d : TraceRecord {
        attribute :>> elementId = "F-4413-01";
        attribute :>> sourceFile = "Rail_MBSE_Function_Interface_v1_final.xlsx";
        attribute :>> sourceSheet = "Function";
        attribute :>> sourceRow = 59;
    }
    item trace_251cef0e726a88b9 : TraceRecord {
        attribute :>> elementId = "F-4500-01";
        attribute :>> sourceFile = "Rail_MBSE_Function_Interface_v1_final.xlsx";
        attribute :>> sourceSheet = "Function";
        attribute :>> sourceRow = 60;
    }
    item trace_531cf26135acd0e4 : TraceRecord {
        attribute :>> elementId = "F-4510-01";
        attribute :>> sourceFile = "Rail_MBSE_Function_Interface_v1_final.xlsx";
        attribute :>> sourceSheet = "Function";
        attribute :>> sourceRow = 61;
    }
    item trace_16a7fdc3cb42251b : TraceRecord {
        attribute :>> elementId = "F-4511-01";
        attribute :>> sourceFile = "Rail_MBSE_Function_Interface_v1_final.xlsx";
        attribute :>> sourceSheet = "Function";
        attribute :>> sourceRow = 62;
    }
    item trace_f868969b9086572b : TraceRecord {
        attribute :>> elementId = "F-4513-01";
        attribute :>> sourceFile = "Rail_MBSE_Function_Interface_v1_final.xlsx";
        attribute :>> sourceSheet = "Function";
        attribute :>> sourceRow = 63;
    }
    item trace_03153048105a176f : TraceRecord {
        attribute :>> elementId = "F-4517-01";
        attribute :>> sourceFile = "Rail_MBSE_Function_Interface_v1_final.xlsx";
        attribute :>> sourceSheet = "Function";
        attribute :>> sourceRow = 64;
    }
    item trace_34ae21e5934cdd2f : TraceRecord {
        attribute :>> elementId = "F-4518-01";
        attribute :>> sourceFile = "Rail_MBSE_Function_Interface_v1_final.xlsx";
        attribute :>> sourceSheet = "Function";
        attribute :>> sourceRow = 65;
    }
    item trace_04929025b4b5a18e : TraceRecord {
        attribute :>> elementId = "F-4518-02";
        attribute :>> sourceFile = "Rail_MBSE_Function_Interface_v1_final.xlsx";
        attribute :>> sourceSheet = "Function";
        attribute :>> sourceRow = 66;
    }
    item trace_2eef8bca5dbbe5f6 : TraceRecord {
        attribute :>> elementId = "F-5000-01";
        attribute :>> sourceFile = "Rail_MBSE_Function_Interface_v1_final.xlsx";
        attribute :>> sourceSheet = "Function";
        attribute :>> sourceRow = 67;
    }
    item trace_be596f9e91d4ec6c : TraceRecord {
        attribute :>> elementId = "F-5100-01";
        attribute :>> sourceFile = "Rail_MBSE_Function_Interface_v1_final.xlsx";
        attribute :>> sourceSheet = "Function";
        attribute :>> sourceRow = 68;
    }
    item trace_39622b435632172d : TraceRecord {
        attribute :>> elementId = "F-5110-01";
        attribute :>> sourceFile = "Rail_MBSE_Function_Interface_v1_final.xlsx";
        attribute :>> sourceSheet = "Function";
        attribute :>> sourceRow = 69;
    }
    item trace_43618bcb810e6839 : TraceRecord {
        attribute :>> elementId = "F-5111-01";
        attribute :>> sourceFile = "Rail_MBSE_Function_Interface_v1_final.xlsx";
        attribute :>> sourceSheet = "Function";
        attribute :>> sourceRow = 70;
    }
    item trace_51b6e56722859a11 : TraceRecord {
        attribute :>> elementId = "F-5111-02";
        attribute :>> sourceFile = "Rail_MBSE_Function_Interface_v1_final.xlsx";
        attribute :>> sourceSheet = "Function";
        attribute :>> sourceRow = 71;
    }
    item trace_8881db023b5f73b0 : TraceRecord {
        attribute :>> elementId = "F-5111-03";
        attribute :>> sourceFile = "Rail_MBSE_Function_Interface_v1_final.xlsx";
        attribute :>> sourceSheet = "Function";
        attribute :>> sourceRow = 72;
    }
    item trace_7289a7f4f45ee9e7 : TraceRecord {
        attribute :>> elementId = "F-5111-04";
        attribute :>> sourceFile = "Rail_MBSE_Function_Interface_v1_final.xlsx";
        attribute :>> sourceSheet = "Function";
        attribute :>> sourceRow = 73;
    }
    item trace_ec81b2bba91ea9d3 : TraceRecord {
        attribute :>> elementId = "F-5112-01";
        attribute :>> sourceFile = "Rail_MBSE_Function_Interface_v1_final.xlsx";
        attribute :>> sourceSheet = "Function";
        attribute :>> sourceRow = 74;
    }
    item trace_276d1a25a793ccb8 : TraceRecord {
        attribute :>> elementId = "F-5112-02";
        attribute :>> sourceFile = "Rail_MBSE_Function_Interface_v1_final.xlsx";
        attribute :>> sourceSheet = "Function";
        attribute :>> sourceRow = 75;
    }
    item trace_b06f894e16cb0fe3 : TraceRecord {
        attribute :>> elementId = "F-5112-03";
        attribute :>> sourceFile = "Rail_MBSE_Function_Interface_v1_final.xlsx";
        attribute :>> sourceSheet = "Function";
        attribute :>> sourceRow = 76;
    }
    item trace_8480630e6a4fae98 : TraceRecord {
        attribute :>> elementId = "F-5112-04";
        attribute :>> sourceFile = "Rail_MBSE_Function_Interface_v1_final.xlsx";
        attribute :>> sourceSheet = "Function";
        attribute :>> sourceRow = 77;
    }
    item trace_e0229f02e844bd26 : TraceRecord {
        attribute :>> elementId = "F-5113-01";
        attribute :>> sourceFile = "Rail_MBSE_Function_Interface_v1_final.xlsx";
        attribute :>> sourceSheet = "Function";
        attribute :>> sourceRow = 78;
    }
    item trace_1593ac3189e30ffe : TraceRecord {
        attribute :>> elementId = "F-5120-01";
        attribute :>> sourceFile = "Rail_MBSE_Function_Interface_v1_final.xlsx";
        attribute :>> sourceSheet = "Function";
        attribute :>> sourceRow = 79;
    }
    item trace_59e4245e937e9895 : TraceRecord {
        attribute :>> elementId = "F-5121-01";
        attribute :>> sourceFile = "Rail_MBSE_Function_Interface_v1_final.xlsx";
        attribute :>> sourceSheet = "Function";
        attribute :>> sourceRow = 80;
    }
    item trace_b059eee66f305927 : TraceRecord {
        attribute :>> elementId = "F-5122-01";
        attribute :>> sourceFile = "Rail_MBSE_Function_Interface_v1_final.xlsx";
        attribute :>> sourceSheet = "Function";
        attribute :>> sourceRow = 81;
    }
    item trace_ffb62741463685a6 : TraceRecord {
        attribute :>> elementId = "F-5130-01";
        attribute :>> sourceFile = "Rail_MBSE_Function_Interface_v1_final.xlsx";
        attribute :>> sourceSheet = "Function";
        attribute :>> sourceRow = 82;
    }
    item trace_43d7315cfaebb138 : TraceRecord {
        attribute :>> elementId = "F-5131-01";
        attribute :>> sourceFile = "Rail_MBSE_Function_Interface_v1_final.xlsx";
        attribute :>> sourceSheet = "Function";
        attribute :>> sourceRow = 83;
    }
    item trace_8a4eb8f414aa3439 : TraceRecord {
        attribute :>> elementId = "F-5131-02";
        attribute :>> sourceFile = "Rail_MBSE_Function_Interface_v1_final.xlsx";
        attribute :>> sourceSheet = "Function";
        attribute :>> sourceRow = 84;
    }
    item trace_df3c2b7e2ab1be04 : TraceRecord {
        attribute :>> elementId = "F-5132-01";
        attribute :>> sourceFile = "Rail_MBSE_Function_Interface_v1_final.xlsx";
        attribute :>> sourceSheet = "Function";
        attribute :>> sourceRow = 85;
    }
    item trace_29952fb27a098b27 : TraceRecord {
        attribute :>> elementId = "F-5132-02";
        attribute :>> sourceFile = "Rail_MBSE_Function_Interface_v1_final.xlsx";
        attribute :>> sourceSheet = "Function";
        attribute :>> sourceRow = 86;
    }
    item trace_de4a97ba95726060 : TraceRecord {
        attribute :>> elementId = "F-5133-01";
        attribute :>> sourceFile = "Rail_MBSE_Function_Interface_v1_final.xlsx";
        attribute :>> sourceSheet = "Function";
        attribute :>> sourceRow = 87;
    }
    item trace_fcf8c8072d3ac918 : TraceRecord {
        attribute :>> elementId = "F-5133-02";
        attribute :>> sourceFile = "Rail_MBSE_Function_Interface_v1_final.xlsx";
        attribute :>> sourceSheet = "Function";
        attribute :>> sourceRow = 88;
    }
    item trace_4fd44a44f1b58de5 : TraceRecord {
        attribute :>> elementId = "F-5133-03";
        attribute :>> sourceFile = "Rail_MBSE_Function_Interface_v1_final.xlsx";
        attribute :>> sourceSheet = "Function";
        attribute :>> sourceRow = 89;
    }
    item trace_a3b8a35ffd50287e : TraceRecord {
        attribute :>> elementId = "F-5140-01";
        attribute :>> sourceFile = "Rail_MBSE_Function_Interface_v1_final.xlsx";
        attribute :>> sourceSheet = "Function";
        attribute :>> sourceRow = 90;
    }
    item trace_061e9dc87ef28117 : TraceRecord {
        attribute :>> elementId = "F-5142-01";
        attribute :>> sourceFile = "Rail_MBSE_Function_Interface_v1_final.xlsx";
        attribute :>> sourceSheet = "Function";
        attribute :>> sourceRow = 91;
    }
    item trace_5b5bfd185c23aca7 : TraceRecord {
        attribute :>> elementId = "F-5142-02";
        attribute :>> sourceFile = "Rail_MBSE_Function_Interface_v1_final.xlsx";
        attribute :>> sourceSheet = "Function";
        attribute :>> sourceRow = 92;
    }
    item trace_09456f5a1df50984 : TraceRecord {
        attribute :>> elementId = "F-5145-01";
        attribute :>> sourceFile = "Rail_MBSE_Function_Interface_v1_final.xlsx";
        attribute :>> sourceSheet = "Function";
        attribute :>> sourceRow = 93;
    }
    item trace_b0b521f74d8dc05b : TraceRecord {
        attribute :>> elementId = "F-5300-01";
        attribute :>> sourceFile = "Rail_MBSE_Function_Interface_v1_final.xlsx";
        attribute :>> sourceSheet = "Function";
        attribute :>> sourceRow = 94;
    }
    item trace_5b9d9a2cf928523e : TraceRecord {
        attribute :>> elementId = "F-5310-01";
        attribute :>> sourceFile = "Rail_MBSE_Function_Interface_v1_final.xlsx";
        attribute :>> sourceSheet = "Function";
        attribute :>> sourceRow = 95;
    }
    item trace_f739d34ff7059f9d : TraceRecord {
        attribute :>> elementId = "F-5311-01";
        attribute :>> sourceFile = "Rail_MBSE_Function_Interface_v1_final.xlsx";
        attribute :>> sourceSheet = "Function";
        attribute :>> sourceRow = 96;
    }
    item trace_a118b2731861a90f : TraceRecord {
        attribute :>> elementId = "F-5311-02";
        attribute :>> sourceFile = "Rail_MBSE_Function_Interface_v1_final.xlsx";
        attribute :>> sourceSheet = "Function";
        attribute :>> sourceRow = 97;
    }
    item trace_207cf0f3fccf9a78 : TraceRecord {
        attribute :>> elementId = "F-7000-01";
        attribute :>> sourceFile = "Rail_MBSE_Function_Interface_v1_final.xlsx";
        attribute :>> sourceSheet = "Function";
        attribute :>> sourceRow = 98;
    }
    item trace_ad1452c2d65cca20 : TraceRecord {
        attribute :>> elementId = "F-7100-01";
        attribute :>> sourceFile = "Rail_MBSE_Function_Interface_v1_final.xlsx";
        attribute :>> sourceSheet = "Function";
        attribute :>> sourceRow = 99;
    }
    item trace_e7a9292188328e78 : TraceRecord {
        attribute :>> elementId = "F-7120-01";
        attribute :>> sourceFile = "Rail_MBSE_Function_Interface_v1_final.xlsx";
        attribute :>> sourceSheet = "Function";
        attribute :>> sourceRow = 100;
    }
    item trace_b88b05e9115a5dd8 : TraceRecord {
        attribute :>> elementId = "F-7124-01";
        attribute :>> sourceFile = "Rail_MBSE_Function_Interface_v1_final.xlsx";
        attribute :>> sourceSheet = "Function";
        attribute :>> sourceRow = 101;
    }
    item trace_150c230a69635f0b : TraceRecord {
        attribute :>> elementId = "F-7130-01";
        attribute :>> sourceFile = "Rail_MBSE_Function_Interface_v1_final.xlsx";
        attribute :>> sourceSheet = "Function";
        attribute :>> sourceRow = 102;
    }
    item trace_6dc166d730f166ed : TraceRecord {
        attribute :>> elementId = "F-7131-01";
        attribute :>> sourceFile = "Rail_MBSE_Function_Interface_v1_final.xlsx";
        attribute :>> sourceSheet = "Function";
        attribute :>> sourceRow = 103;
    }
    item trace_78627de4e69df1b8 : TraceRecord {
        attribute :>> elementId = "F-7140-01";
        attribute :>> sourceFile = "Rail_MBSE_Function_Interface_v1_final.xlsx";
        attribute :>> sourceSheet = "Function";
        attribute :>> sourceRow = 104;
    }
    item trace_7a39ae8039882bfd : TraceRecord {
        attribute :>> elementId = "F-7142-01";
        attribute :>> sourceFile = "Rail_MBSE_Function_Interface_v1_final.xlsx";
        attribute :>> sourceSheet = "Function";
        attribute :>> sourceRow = 105;
    }
    item trace_9d4811c30321619f : TraceRecord {
        attribute :>> elementId = "F-7200-01";
        attribute :>> sourceFile = "Rail_MBSE_Function_Interface_v1_final.xlsx";
        attribute :>> sourceSheet = "Function";
        attribute :>> sourceRow = 106;
    }
    item trace_10817670dd2fd8c8 : TraceRecord {
        attribute :>> elementId = "F-7210-01";
        attribute :>> sourceFile = "Rail_MBSE_Function_Interface_v1_final.xlsx";
        attribute :>> sourceSheet = "Function";
        attribute :>> sourceRow = 107;
    }
    item trace_b6e937c7fc96fd5b : TraceRecord {
        attribute :>> elementId = "F-7211-01";
        attribute :>> sourceFile = "Rail_MBSE_Function_Interface_v1_final.xlsx";
        attribute :>> sourceSheet = "Function";
        attribute :>> sourceRow = 108;
    }
    item trace_5f8638fbd3afc2a4 : TraceRecord {
        attribute :>> elementId = "F-7211-02";
        attribute :>> sourceFile = "Rail_MBSE_Function_Interface_v1_final.xlsx";
        attribute :>> sourceSheet = "Function";
        attribute :>> sourceRow = 109;
    }
    item trace_a349e38fa2427d38 : TraceRecord {
        attribute :>> elementId = "F-7211-03";
        attribute :>> sourceFile = "Rail_MBSE_Function_Interface_v1_final.xlsx";
        attribute :>> sourceSheet = "Function";
        attribute :>> sourceRow = 110;
    }
    item trace_48a65a6f82f1dcba : TraceRecord {
        attribute :>> elementId = "F-7211-04";
        attribute :>> sourceFile = "Rail_MBSE_Function_Interface_v1_final.xlsx";
        attribute :>> sourceSheet = "Function";
        attribute :>> sourceRow = 111;
    }
    item trace_fd6537c268718098 : TraceRecord {
        attribute :>> elementId = "F-7213-01";
        attribute :>> sourceFile = "Rail_MBSE_Function_Interface_v1_final.xlsx";
        attribute :>> sourceSheet = "Function";
        attribute :>> sourceRow = 112;
    }
    item trace_8f7818a83cb4b58c : TraceRecord {
        attribute :>> elementId = "F-7220-01";
        attribute :>> sourceFile = "Rail_MBSE_Function_Interface_v1_final.xlsx";
        attribute :>> sourceSheet = "Function";
        attribute :>> sourceRow = 113;
    }
    item trace_41aac5474e431bb8 : TraceRecord {
        attribute :>> elementId = "F-7222-01";
        attribute :>> sourceFile = "Rail_MBSE_Function_Interface_v1_final.xlsx";
        attribute :>> sourceSheet = "Function";
        attribute :>> sourceRow = 114;
    }
    item trace_7f23f7e6f9bc61c0 : TraceRecord {
        attribute :>> elementId = "F-7223-01";
        attribute :>> sourceFile = "Rail_MBSE_Function_Interface_v1_final.xlsx";
        attribute :>> sourceSheet = "Function";
        attribute :>> sourceRow = 115;
    }
    item trace_68b66ef4e22b6e46 : TraceRecord {
        attribute :>> elementId = "F-7224-01";
        attribute :>> sourceFile = "Rail_MBSE_Function_Interface_v1_final.xlsx";
        attribute :>> sourceSheet = "Function";
        attribute :>> sourceRow = 116;
    }
    item trace_71e3e004c34fefd3 : TraceRecord {
        attribute :>> elementId = "F-7225-01";
        attribute :>> sourceFile = "Rail_MBSE_Function_Interface_v1_final.xlsx";
        attribute :>> sourceSheet = "Function";
        attribute :>> sourceRow = 117;
    }
    item trace_1036347064b6c77f : TraceRecord {
        attribute :>> elementId = "F-7226-01";
        attribute :>> sourceFile = "Rail_MBSE_Function_Interface_v1_final.xlsx";
        attribute :>> sourceSheet = "Function";
        attribute :>> sourceRow = 118;
    }
    item trace_bf3507627243d683 : TraceRecord {
        attribute :>> elementId = "F-7227-01";
        attribute :>> sourceFile = "Rail_MBSE_Function_Interface_v1_final.xlsx";
        attribute :>> sourceSheet = "Function";
        attribute :>> sourceRow = 119;
    }
    item trace_c63f36a5a4f9802b : TraceRecord {
        attribute :>> elementId = "F-7228-01";
        attribute :>> sourceFile = "Rail_MBSE_Function_Interface_v1_final.xlsx";
        attribute :>> sourceSheet = "Function";
        attribute :>> sourceRow = 120;
    }
    item trace_35e84546c9f5ea46 : TraceRecord {
        attribute :>> elementId = "F-7229-01";
        attribute :>> sourceFile = "Rail_MBSE_Function_Interface_v1_final.xlsx";
        attribute :>> sourceSheet = "Function";
        attribute :>> sourceRow = 121;
    }
    item trace_6039ced9411bc570 : TraceRecord {
        attribute :>> elementId = "F-722A-01";
        attribute :>> sourceFile = "Rail_MBSE_Function_Interface_v1_final.xlsx";
        attribute :>> sourceSheet = "Function";
        attribute :>> sourceRow = 122;
    }
    item trace_bb29827b64dd4ab4 : TraceRecord {
        attribute :>> elementId = "F-722B-01";
        attribute :>> sourceFile = "Rail_MBSE_Function_Interface_v1_final.xlsx";
        attribute :>> sourceSheet = "Function";
        attribute :>> sourceRow = 123;
    }
    item trace_8f954f0f54ab8364 : TraceRecord {
        attribute :>> elementId = "F-722C-01";
        attribute :>> sourceFile = "Rail_MBSE_Function_Interface_v1_final.xlsx";
        attribute :>> sourceSheet = "Function";
        attribute :>> sourceRow = 124;
    }
    item trace_98183d647c443c61 : TraceRecord {
        attribute :>> elementId = "F-7250-01";
        attribute :>> sourceFile = "Rail_MBSE_Function_Interface_v1_final.xlsx";
        attribute :>> sourceSheet = "Function";
        attribute :>> sourceRow = 125;
    }
    item trace_f5fba43e2b2c3857 : TraceRecord {
        attribute :>> elementId = "F-7252-01";
        attribute :>> sourceFile = "Rail_MBSE_Function_Interface_v1_final.xlsx";
        attribute :>> sourceSheet = "Function";
        attribute :>> sourceRow = 126;
    }
    item trace_becbc67a1ea3860c : TraceRecord {
        attribute :>> elementId = "F-7254-01";
        attribute :>> sourceFile = "Rail_MBSE_Function_Interface_v1_final.xlsx";
        attribute :>> sourceSheet = "Function";
        attribute :>> sourceRow = 127;
    }
    item trace_9d0edc72ee0c8281 : TraceRecord {
        attribute :>> elementId = "F-7255-01";
        attribute :>> sourceFile = "Rail_MBSE_Function_Interface_v1_final.xlsx";
        attribute :>> sourceSheet = "Function";
        attribute :>> sourceRow = 128;
    }
    item trace_d57a82130ad1aa08 : TraceRecord {
        attribute :>> elementId = "F-7280-01";
        attribute :>> sourceFile = "Rail_MBSE_Function_Interface_v1_final.xlsx";
        attribute :>> sourceSheet = "Function";
        attribute :>> sourceRow = 129;
    }
    item trace_102540ab1572f011 : TraceRecord {
        attribute :>> elementId = "F-7281-01";
        attribute :>> sourceFile = "Rail_MBSE_Function_Interface_v1_final.xlsx";
        attribute :>> sourceSheet = "Function";
        attribute :>> sourceRow = 130;
    }
    item trace_5e3cee6da5a6d99a : TraceRecord {
        attribute :>> elementId = "F-7284-01";
        attribute :>> sourceFile = "Rail_MBSE_Function_Interface_v1_final.xlsx";
        attribute :>> sourceSheet = "Function";
        attribute :>> sourceRow = 131;
    }
    item trace_1f75776602c1fc36 : TraceRecord {
        attribute :>> elementId = "F-7285-01";
        attribute :>> sourceFile = "Rail_MBSE_Function_Interface_v1_final.xlsx";
        attribute :>> sourceSheet = "Function";
        attribute :>> sourceRow = 132;
    }
    item trace_e8ff46d0f3c1e399 : TraceRecord {
        attribute :>> elementId = "F-8000-01";
        attribute :>> sourceFile = "Rail_MBSE_Function_Interface_v1_final.xlsx";
        attribute :>> sourceSheet = "Function";
        attribute :>> sourceRow = 133;
    }
    item trace_fc04cfaa90e2e76b : TraceRecord {
        attribute :>> elementId = "F-8100-01";
        attribute :>> sourceFile = "Rail_MBSE_Function_Interface_v1_final.xlsx";
        attribute :>> sourceSheet = "Function";
        attribute :>> sourceRow = 134;
    }
    item trace_6e37d3a0f5393e78 : TraceRecord {
        attribute :>> elementId = "F-8120-01";
        attribute :>> sourceFile = "Rail_MBSE_Function_Interface_v1_final.xlsx";
        attribute :>> sourceSheet = "Function";
        attribute :>> sourceRow = 135;
    }
    item trace_5b715a9464fae97c : TraceRecord {
        attribute :>> elementId = "F-8121-01";
        attribute :>> sourceFile = "Rail_MBSE_Function_Interface_v1_final.xlsx";
        attribute :>> sourceSheet = "Function";
        attribute :>> sourceRow = 136;
    }
    item trace_2533559b7fe1b6a8 : TraceRecord {
        attribute :>> elementId = "F-8121-02";
        attribute :>> sourceFile = "Rail_MBSE_Function_Interface_v1_final.xlsx";
        attribute :>> sourceSheet = "Function";
        attribute :>> sourceRow = 137;
    }
    item trace_1fe52ba196785817 : TraceRecord {
        attribute :>> elementId = "F-8121-03";
        attribute :>> sourceFile = "Rail_MBSE_Function_Interface_v1_final.xlsx";
        attribute :>> sourceSheet = "Function";
        attribute :>> sourceRow = 138;
    }
    item trace_cd82b564f0e2a5de : TraceRecord {
        attribute :>> elementId = "F-8122-01";
        attribute :>> sourceFile = "Rail_MBSE_Function_Interface_v1_final.xlsx";
        attribute :>> sourceSheet = "Function";
        attribute :>> sourceRow = 139;
    }
    item trace_8ebdec1f392f346b : TraceRecord {
        attribute :>> elementId = "F-8122-02";
        attribute :>> sourceFile = "Rail_MBSE_Function_Interface_v1_final.xlsx";
        attribute :>> sourceSheet = "Function";
        attribute :>> sourceRow = 140;
    }
    item trace_55ac96407c9b0efb : TraceRecord {
        attribute :>> elementId = "F-8122-03";
        attribute :>> sourceFile = "Rail_MBSE_Function_Interface_v1_final.xlsx";
        attribute :>> sourceSheet = "Function";
        attribute :>> sourceRow = 141;
    }
    item trace_61a8f4bfd1ffd96f : TraceRecord {
        attribute :>> elementId = "F-8122-04";
        attribute :>> sourceFile = "Rail_MBSE_Function_Interface_v1_final.xlsx";
        attribute :>> sourceSheet = "Function";
        attribute :>> sourceRow = 142;
    }
    item trace_857429e054c8d15d : TraceRecord {
        attribute :>> elementId = "F-8122-05";
        attribute :>> sourceFile = "Rail_MBSE_Function_Interface_v1_final.xlsx";
        attribute :>> sourceSheet = "Function";
        attribute :>> sourceRow = 143;
    }
    item trace_9f058551755f829b : TraceRecord {
        attribute :>> elementId = "F-8125-01";
        attribute :>> sourceFile = "Rail_MBSE_Function_Interface_v1_final.xlsx";
        attribute :>> sourceSheet = "Function";
        attribute :>> sourceRow = 144;
    }
    item trace_34219d847e624734 : TraceRecord {
        attribute :>> elementId = "F-8125-02";
        attribute :>> sourceFile = "Rail_MBSE_Function_Interface_v1_final.xlsx";
        attribute :>> sourceSheet = "Function";
        attribute :>> sourceRow = 145;
    }
    item trace_b84c725475b1f73b : TraceRecord {
        attribute :>> elementId = "F-8125-03";
        attribute :>> sourceFile = "Rail_MBSE_Function_Interface_v1_final.xlsx";
        attribute :>> sourceSheet = "Function";
        attribute :>> sourceRow = 146;
    }
    item trace_9d5be619340d5381 : TraceRecord {
        attribute :>> elementId = "F-8125-04";
        attribute :>> sourceFile = "Rail_MBSE_Function_Interface_v1_final.xlsx";
        attribute :>> sourceSheet = "Function";
        attribute :>> sourceRow = 147;
    }
    item trace_d0ac7291708a34f3 : TraceRecord {
        attribute :>> elementId = "F-8127-01";
        attribute :>> sourceFile = "Rail_MBSE_Function_Interface_v1_final.xlsx";
        attribute :>> sourceSheet = "Function";
        attribute :>> sourceRow = 148;
    }
    item trace_7356c1c529d30dfe : TraceRecord {
        attribute :>> elementId = "F-8127-02";
        attribute :>> sourceFile = "Rail_MBSE_Function_Interface_v1_final.xlsx";
        attribute :>> sourceSheet = "Function";
        attribute :>> sourceRow = 149;
    }
    item trace_6a7d8cbaa721b822 : TraceRecord {
        attribute :>> elementId = "F-8128-01";
        attribute :>> sourceFile = "Rail_MBSE_Function_Interface_v1_final.xlsx";
        attribute :>> sourceSheet = "Function";
        attribute :>> sourceRow = 150;
    }
    item trace_de775af53eff7c82 : TraceRecord {
        attribute :>> elementId = "F-8128-02";
        attribute :>> sourceFile = "Rail_MBSE_Function_Interface_v1_final.xlsx";
        attribute :>> sourceSheet = "Function";
        attribute :>> sourceRow = 151;
    }
    item trace_a931e90def707924 : TraceRecord {
        attribute :>> elementId = "F-8128-03";
        attribute :>> sourceFile = "Rail_MBSE_Function_Interface_v1_final.xlsx";
        attribute :>> sourceSheet = "Function";
        attribute :>> sourceRow = 152;
    }
    item trace_31daa08839653f95 : TraceRecord {
        attribute :>> elementId = "F-8150-01";
        attribute :>> sourceFile = "Rail_MBSE_Function_Interface_v1_final.xlsx";
        attribute :>> sourceSheet = "Function";
        attribute :>> sourceRow = 153;
    }
    item trace_9f7d49b82dfdd3c8 : TraceRecord {
        attribute :>> elementId = "F-8151-01";
        attribute :>> sourceFile = "Rail_MBSE_Function_Interface_v1_final.xlsx";
        attribute :>> sourceSheet = "Function";
        attribute :>> sourceRow = 154;
    }
    item trace_122cdfb91d4938ae : TraceRecord {
        attribute :>> elementId = "F-8151-02";
        attribute :>> sourceFile = "Rail_MBSE_Function_Interface_v1_final.xlsx";
        attribute :>> sourceSheet = "Function";
        attribute :>> sourceRow = 155;
    }
    item trace_3ac0cae4590f7def : TraceRecord {
        attribute :>> elementId = "F-8152-01";
        attribute :>> sourceFile = "Rail_MBSE_Function_Interface_v1_final.xlsx";
        attribute :>> sourceSheet = "Function";
        attribute :>> sourceRow = 156;
    }
    item trace_1ceebf6764c47d14 : TraceRecord {
        attribute :>> elementId = "F-8152-02";
        attribute :>> sourceFile = "Rail_MBSE_Function_Interface_v1_final.xlsx";
        attribute :>> sourceSheet = "Function";
        attribute :>> sourceRow = 157;
    }
    item trace_3dfef2a2e95a9479 : TraceRecord {
        attribute :>> elementId = "F-8154-01";
        attribute :>> sourceFile = "Rail_MBSE_Function_Interface_v1_final.xlsx";
        attribute :>> sourceSheet = "Function";
        attribute :>> sourceRow = 158;
    }
    item trace_c53e263848a6b025 : TraceRecord {
        attribute :>> elementId = "F-8154-02";
        attribute :>> sourceFile = "Rail_MBSE_Function_Interface_v1_final.xlsx";
        attribute :>> sourceSheet = "Function";
        attribute :>> sourceRow = 159;
    }
    item trace_449eaefed29b5d05 : TraceRecord {
        attribute :>> elementId = "F-8160-01";
        attribute :>> sourceFile = "Rail_MBSE_Function_Interface_v1_final.xlsx";
        attribute :>> sourceSheet = "Function";
        attribute :>> sourceRow = 160;
    }
    item trace_78da722fae3d0e70 : TraceRecord {
        attribute :>> elementId = "F-8166-01";
        attribute :>> sourceFile = "Rail_MBSE_Function_Interface_v1_final.xlsx";
        attribute :>> sourceSheet = "Function";
        attribute :>> sourceRow = 161;
    }
    item trace_3180c02f6ad9e0ad : TraceRecord {
        attribute :>> elementId = "F-8166-02";
        attribute :>> sourceFile = "Rail_MBSE_Function_Interface_v1_final.xlsx";
        attribute :>> sourceSheet = "Function";
        attribute :>> sourceRow = 162;
    }
    item trace_d92ea65d30e5d911 : TraceRecord {
        attribute :>> elementId = "F-8166-03";
        attribute :>> sourceFile = "Rail_MBSE_Function_Interface_v1_final.xlsx";
        attribute :>> sourceSheet = "Function";
        attribute :>> sourceRow = 163;
    }
    item trace_a767e8c9af66502e : TraceRecord {
        attribute :>> elementId = "F-8166-04";
        attribute :>> sourceFile = "Rail_MBSE_Function_Interface_v1_final.xlsx";
        attribute :>> sourceSheet = "Function";
        attribute :>> sourceRow = 164;
    }
    item trace_c981bc3f6588c7c9 : TraceRecord {
        attribute :>> elementId = "F-D000-01";
        attribute :>> sourceFile = "Rail_MBSE_Function_Interface_v1_final.xlsx";
        attribute :>> sourceSheet = "Function";
        attribute :>> sourceRow = 165;
    }
    item trace_6a894f0d8de0c13e : TraceRecord {
        attribute :>> elementId = "F-D100-01";
        attribute :>> sourceFile = "Rail_MBSE_Function_Interface_v1_final.xlsx";
        attribute :>> sourceSheet = "Function";
        attribute :>> sourceRow = 166;
    }
    item trace_640d19113041fad5 : TraceRecord {
        attribute :>> elementId = "F-D110-01";
        attribute :>> sourceFile = "Rail_MBSE_Function_Interface_v1_final.xlsx";
        attribute :>> sourceSheet = "Function";
        attribute :>> sourceRow = 167;
    }
    item trace_08c124b7dcf90b72 : TraceRecord {
        attribute :>> elementId = "F-D112-01";
        attribute :>> sourceFile = "Rail_MBSE_Function_Interface_v1_final.xlsx";
        attribute :>> sourceSheet = "Function";
        attribute :>> sourceRow = 168;
    }
    item trace_a386dff27b8b9164 : TraceRecord {
        attribute :>> elementId = "F-D113-01";
        attribute :>> sourceFile = "Rail_MBSE_Function_Interface_v1_final.xlsx";
        attribute :>> sourceSheet = "Function";
        attribute :>> sourceRow = 169;
    }
    item trace_5e8303800da85866 : TraceRecord {
        attribute :>> elementId = "F-D114-01";
        attribute :>> sourceFile = "Rail_MBSE_Function_Interface_v1_final.xlsx";
        attribute :>> sourceSheet = "Function";
        attribute :>> sourceRow = 170;
    }
    item trace_d08a11ca99e08246 : TraceRecord {
        attribute :>> elementId = "F-D120-01";
        attribute :>> sourceFile = "Rail_MBSE_Function_Interface_v1_final.xlsx";
        attribute :>> sourceSheet = "Function";
        attribute :>> sourceRow = 171;
    }
    item trace_f38d0bfbc5bf2b2e : TraceRecord {
        attribute :>> elementId = "F-D121-01";
        attribute :>> sourceFile = "Rail_MBSE_Function_Interface_v1_final.xlsx";
        attribute :>> sourceSheet = "Function";
        attribute :>> sourceRow = 172;
    }
    item trace_f2e0762ef2adcb52 : TraceRecord {
        attribute :>> elementId = "F-D130-01";
        attribute :>> sourceFile = "Rail_MBSE_Function_Interface_v1_final.xlsx";
        attribute :>> sourceSheet = "Function";
        attribute :>> sourceRow = 173;
    }
    item trace_89844015628e4c98 : TraceRecord {
        attribute :>> elementId = "F-D13B-01";
        attribute :>> sourceFile = "Rail_MBSE_Function_Interface_v1_final.xlsx";
        attribute :>> sourceSheet = "Function";
        attribute :>> sourceRow = 174;
    }
    item trace_8876d46f5b14c46b : TraceRecord {
        attribute :>> elementId = "F-E000-01";
        attribute :>> sourceFile = "Rail_MBSE_Function_Interface_v1_final.xlsx";
        attribute :>> sourceSheet = "Function";
        attribute :>> sourceRow = 175;
    }
    item trace_640e184c9f3270ce : TraceRecord {
        attribute :>> elementId = "F-E100-01";
        attribute :>> sourceFile = "Rail_MBSE_Function_Interface_v1_final.xlsx";
        attribute :>> sourceSheet = "Function";
        attribute :>> sourceRow = 176;
    }
    item trace_9ab2c13aa0cd0b37 : TraceRecord {
        attribute :>> elementId = "F-X000-01";
        attribute :>> sourceFile = "Rail_MBSE_Function_Interface_v1_final.xlsx";
        attribute :>> sourceSheet = "Function";
        attribute :>> sourceRow = 177;
    }
    item trace_de2134433732cce0 : TraceRecord {
        attribute :>> elementId = "F-X100-01";
        attribute :>> sourceFile = "Rail_MBSE_Function_Interface_v1_final.xlsx";
        attribute :>> sourceSheet = "Function";
        attribute :>> sourceRow = 178;
    }
    item trace_e6d299e382875f9a : TraceRecord {
        attribute :>> elementId = "F-X110-01";
        attribute :>> sourceFile = "Rail_MBSE_Function_Interface_v1_final.xlsx";
        attribute :>> sourceSheet = "Function";
        attribute :>> sourceRow = 179;
    }
    item trace_7f475ed50ea267dd : TraceRecord {
        attribute :>> elementId = "F-X111-01";
        attribute :>> sourceFile = "Rail_MBSE_Function_Interface_v1_final.xlsx";
        attribute :>> sourceSheet = "Function";
        attribute :>> sourceRow = 180;
    }
    item trace_4c3fecd7f511b146 : TraceRecord {
        attribute :>> elementId = "F-X111-02";
        attribute :>> sourceFile = "Rail_MBSE_Function_Interface_v1_final.xlsx";
        attribute :>> sourceSheet = "Function";
        attribute :>> sourceRow = 181;
    }
    item trace_7fa73ab0b7adb64c : TraceRecord {
        attribute :>> elementId = "F-X112-01";
        attribute :>> sourceFile = "Rail_MBSE_Function_Interface_v1_final.xlsx";
        attribute :>> sourceSheet = "Function";
        attribute :>> sourceRow = 182;
    }
    item trace_90ee521bef9ea5d0 : TraceRecord {
        attribute :>> elementId = "F-X112-02";
        attribute :>> sourceFile = "Rail_MBSE_Function_Interface_v1_final.xlsx";
        attribute :>> sourceSheet = "Function";
        attribute :>> sourceRow = 183;
    }
    item trace_23c4a8c936e239f9 : TraceRecord {
        attribute :>> elementId = "F-X112-03";
        attribute :>> sourceFile = "Rail_MBSE_Function_Interface_v1_final.xlsx";
        attribute :>> sourceSheet = "Function";
        attribute :>> sourceRow = 184;
    }
    item trace_d19d91e15850ad88 : TraceRecord {
        attribute :>> elementId = "F-X113-01";
        attribute :>> sourceFile = "Rail_MBSE_Function_Interface_v1_final.xlsx";
        attribute :>> sourceSheet = "Function";
        attribute :>> sourceRow = 185;
    }
    item trace_d8ee7207b86ba93e : TraceRecord {
        attribute :>> elementId = "F-X120-01";
        attribute :>> sourceFile = "Rail_MBSE_Function_Interface_v1_final.xlsx";
        attribute :>> sourceSheet = "Function";
        attribute :>> sourceRow = 186;
    }
    item trace_7237a824f4c54123 : TraceRecord {
        attribute :>> elementId = "F-X121-01";
        attribute :>> sourceFile = "Rail_MBSE_Function_Interface_v1_final.xlsx";
        attribute :>> sourceSheet = "Function";
        attribute :>> sourceRow = 187;
    }
    item trace_e90c21b1f66ba476 : TraceRecord {
        attribute :>> elementId = "F-X121-02";
        attribute :>> sourceFile = "Rail_MBSE_Function_Interface_v1_final.xlsx";
        attribute :>> sourceSheet = "Function";
        attribute :>> sourceRow = 188;
    }
    item trace_a67d77690b1e7f91 : TraceRecord {
        attribute :>> elementId = "F-X122-01";
        attribute :>> sourceFile = "Rail_MBSE_Function_Interface_v1_final.xlsx";
        attribute :>> sourceSheet = "Function";
        attribute :>> sourceRow = 189;
    }
    item trace_965e9a4ada27a701 : TraceRecord {
        attribute :>> elementId = "F-X123-01";
        attribute :>> sourceFile = "Rail_MBSE_Function_Interface_v1_final.xlsx";
        attribute :>> sourceSheet = "Function";
        attribute :>> sourceRow = 190;
    }
    item trace_46dbde2116861f5a : TraceRecord {
        attribute :>> elementId = "F-X124-01";
        attribute :>> sourceFile = "Rail_MBSE_Function_Interface_v1_final.xlsx";
        attribute :>> sourceSheet = "Function";
        attribute :>> sourceRow = 191;
    }
    item trace_153873802ba7a0a6 : TraceRecord {
        attribute :>> elementId = "F-X130-01";
        attribute :>> sourceFile = "Rail_MBSE_Function_Interface_v1_final.xlsx";
        attribute :>> sourceSheet = "Function";
        attribute :>> sourceRow = 192;
    }
    item trace_b13bc16aacedff61 : TraceRecord {
        attribute :>> elementId = "F-X131-01";
        attribute :>> sourceFile = "Rail_MBSE_Function_Interface_v1_final.xlsx";
        attribute :>> sourceSheet = "Function";
        attribute :>> sourceRow = 193;
    }
    item trace_da41fbe9e993962f : TraceRecord {
        attribute :>> elementId = "F-X132-01";
        attribute :>> sourceFile = "Rail_MBSE_Function_Interface_v1_final.xlsx";
        attribute :>> sourceSheet = "Function";
        attribute :>> sourceRow = 194;
    }
    item trace_f69d5aad7509abbf : TraceRecord {
        attribute :>> elementId = "F-X133-01";
        attribute :>> sourceFile = "Rail_MBSE_Function_Interface_v1_final.xlsx";
        attribute :>> sourceSheet = "Function";
        attribute :>> sourceRow = 195;
    }
    item trace_f691531ef4d3ed3c : TraceRecord {
        attribute :>> elementId = "ALLOC-F-3000-01-3000";
        attribute :>> sourceFile = "Rail_MBSE_Function_Interface_v1_final.xlsx";
        attribute :>> sourceSheet = "Function_Allocation";
        attribute :>> sourceRow = 5;
    }
    item trace_f0a44d72ec70bade : TraceRecord {
        attribute :>> elementId = "ALLOC-F-3100-01-3100";
        attribute :>> sourceFile = "Rail_MBSE_Function_Interface_v1_final.xlsx";
        attribute :>> sourceSheet = "Function_Allocation";
        attribute :>> sourceRow = 6;
    }
    item trace_f604b285cc928d80 : TraceRecord {
        attribute :>> elementId = "ALLOC-F-3110-01-3110";
        attribute :>> sourceFile = "Rail_MBSE_Function_Interface_v1_final.xlsx";
        attribute :>> sourceSheet = "Function_Allocation";
        attribute :>> sourceRow = 7;
    }
    item trace_45554902cb578bc4 : TraceRecord {
        attribute :>> elementId = "ALLOC-F-3111-01-3111";
        attribute :>> sourceFile = "Rail_MBSE_Function_Interface_v1_final.xlsx";
        attribute :>> sourceSheet = "Function_Allocation";
        attribute :>> sourceRow = 8;
    }
    item trace_24fa85314114a026 : TraceRecord {
        attribute :>> elementId = "ALLOC-F-3112-01-3112";
        attribute :>> sourceFile = "Rail_MBSE_Function_Interface_v1_final.xlsx";
        attribute :>> sourceSheet = "Function_Allocation";
        attribute :>> sourceRow = 9;
    }
    item trace_ece4bfe91725d03d : TraceRecord {
        attribute :>> elementId = "ALLOC-F-3120-01-3120";
        attribute :>> sourceFile = "Rail_MBSE_Function_Interface_v1_final.xlsx";
        attribute :>> sourceSheet = "Function_Allocation";
        attribute :>> sourceRow = 10;
    }
    item trace_537224ca53815710 : TraceRecord {
        attribute :>> elementId = "ALLOC-F-3121-01-3121";
        attribute :>> sourceFile = "Rail_MBSE_Function_Interface_v1_final.xlsx";
        attribute :>> sourceSheet = "Function_Allocation";
        attribute :>> sourceRow = 11;
    }
    item trace_5fdae38f81ebdfda : TraceRecord {
        attribute :>> elementId = "ALLOC-F-3130-01-3130";
        attribute :>> sourceFile = "Rail_MBSE_Function_Interface_v1_final.xlsx";
        attribute :>> sourceSheet = "Function_Allocation";
        attribute :>> sourceRow = 12;
    }
    item trace_849d1343f1de8c14 : TraceRecord {
        attribute :>> elementId = "ALLOC-F-3131-01-3131";
        attribute :>> sourceFile = "Rail_MBSE_Function_Interface_v1_final.xlsx";
        attribute :>> sourceSheet = "Function_Allocation";
        attribute :>> sourceRow = 13;
    }
    item trace_799a9bebdd1ed732 : TraceRecord {
        attribute :>> elementId = "ALLOC-F-3132-01-3132";
        attribute :>> sourceFile = "Rail_MBSE_Function_Interface_v1_final.xlsx";
        attribute :>> sourceSheet = "Function_Allocation";
        attribute :>> sourceRow = 14;
    }
    item trace_e68a676dcb6ae4ab : TraceRecord {
        attribute :>> elementId = "ALLOC-F-3133-01-3133";
        attribute :>> sourceFile = "Rail_MBSE_Function_Interface_v1_final.xlsx";
        attribute :>> sourceSheet = "Function_Allocation";
        attribute :>> sourceRow = 15;
    }
    item trace_34c52ee78fb4d3d7 : TraceRecord {
        attribute :>> elementId = "ALLOC-F-3500-01-3500";
        attribute :>> sourceFile = "Rail_MBSE_Function_Interface_v1_final.xlsx";
        attribute :>> sourceSheet = "Function_Allocation";
        attribute :>> sourceRow = 16;
    }
    item trace_ac923df847188cf3 : TraceRecord {
        attribute :>> elementId = "ALLOC-F-3510-01-3510";
        attribute :>> sourceFile = "Rail_MBSE_Function_Interface_v1_final.xlsx";
        attribute :>> sourceSheet = "Function_Allocation";
        attribute :>> sourceRow = 17;
    }
    item trace_90e218d7cbb5385a : TraceRecord {
        attribute :>> elementId = "ALLOC-F-3511-01-3511";
        attribute :>> sourceFile = "Rail_MBSE_Function_Interface_v1_final.xlsx";
        attribute :>> sourceSheet = "Function_Allocation";
        attribute :>> sourceRow = 18;
    }
    item trace_6562181a4384982b : TraceRecord {
        attribute :>> elementId = "ALLOC-F-3512-01-3512";
        attribute :>> sourceFile = "Rail_MBSE_Function_Interface_v1_final.xlsx";
        attribute :>> sourceSheet = "Function_Allocation";
        attribute :>> sourceRow = 19;
    }
    item trace_dfa883b3973c0e17 : TraceRecord {
        attribute :>> elementId = "ALLOC-F-3514-01-3514";
        attribute :>> sourceFile = "Rail_MBSE_Function_Interface_v1_final.xlsx";
        attribute :>> sourceSheet = "Function_Allocation";
        attribute :>> sourceRow = 20;
    }
    item trace_a2551a2e1b0442bd : TraceRecord {
        attribute :>> elementId = "ALLOC-F-3600-01-3600";
        attribute :>> sourceFile = "Rail_MBSE_Function_Interface_v1_final.xlsx";
        attribute :>> sourceSheet = "Function_Allocation";
        attribute :>> sourceRow = 21;
    }
    item trace_e3413ae66123e8c0 : TraceRecord {
        attribute :>> elementId = "ALLOC-F-3640-01-3640";
        attribute :>> sourceFile = "Rail_MBSE_Function_Interface_v1_final.xlsx";
        attribute :>> sourceSheet = "Function_Allocation";
        attribute :>> sourceRow = 22;
    }
    item trace_c6dd34c2ac3ec6a7 : TraceRecord {
        attribute :>> elementId = "ALLOC-F-3641-01-3641";
        attribute :>> sourceFile = "Rail_MBSE_Function_Interface_v1_final.xlsx";
        attribute :>> sourceSheet = "Function_Allocation";
        attribute :>> sourceRow = 23;
    }
    item trace_0a24a90f22b1874a : TraceRecord {
        attribute :>> elementId = "ALLOC-F-3643-01-3643";
        attribute :>> sourceFile = "Rail_MBSE_Function_Interface_v1_final.xlsx";
        attribute :>> sourceSheet = "Function_Allocation";
        attribute :>> sourceRow = 24;
    }
    item trace_6808bc768c090870 : TraceRecord {
        attribute :>> elementId = "ALLOC-F-3644-01-3644";
        attribute :>> sourceFile = "Rail_MBSE_Function_Interface_v1_final.xlsx";
        attribute :>> sourceSheet = "Function_Allocation";
        attribute :>> sourceRow = 25;
    }
    item trace_b34b5cd0c343551d : TraceRecord {
        attribute :>> elementId = "ALLOC-F-3800-01-3800";
        attribute :>> sourceFile = "Rail_MBSE_Function_Interface_v1_final.xlsx";
        attribute :>> sourceSheet = "Function_Allocation";
        attribute :>> sourceRow = 26;
    }
    item trace_f13a2ae4b6f84b39 : TraceRecord {
        attribute :>> elementId = "ALLOC-F-3810-01-3810";
        attribute :>> sourceFile = "Rail_MBSE_Function_Interface_v1_final.xlsx";
        attribute :>> sourceSheet = "Function_Allocation";
        attribute :>> sourceRow = 27;
    }
    item trace_36196bb2ede61a86 : TraceRecord {
        attribute :>> elementId = "ALLOC-F-3811-01-3811";
        attribute :>> sourceFile = "Rail_MBSE_Function_Interface_v1_final.xlsx";
        attribute :>> sourceSheet = "Function_Allocation";
        attribute :>> sourceRow = 28;
    }
    item trace_74b2f29ba6b95aaf : TraceRecord {
        attribute :>> elementId = "ALLOC-F-3811-02-3811";
        attribute :>> sourceFile = "Rail_MBSE_Function_Interface_v1_final.xlsx";
        attribute :>> sourceSheet = "Function_Allocation";
        attribute :>> sourceRow = 29;
    }
    item trace_3b6dc7a99d6a1c77 : TraceRecord {
        attribute :>> elementId = "ALLOC-F-3813-01-3813";
        attribute :>> sourceFile = "Rail_MBSE_Function_Interface_v1_final.xlsx";
        attribute :>> sourceSheet = "Function_Allocation";
        attribute :>> sourceRow = 30;
    }
    item trace_a3e685445f624ff5 : TraceRecord {
        attribute :>> elementId = "ALLOC-F-3814-01-3814";
        attribute :>> sourceFile = "Rail_MBSE_Function_Interface_v1_final.xlsx";
        attribute :>> sourceSheet = "Function_Allocation";
        attribute :>> sourceRow = 31;
    }
    item trace_d49d38e7db013243 : TraceRecord {
        attribute :>> elementId = "ALLOC-F-4000-01-4000";
        attribute :>> sourceFile = "Rail_MBSE_Function_Interface_v1_final.xlsx";
        attribute :>> sourceSheet = "Function_Allocation";
        attribute :>> sourceRow = 32;
    }
    item trace_e312d2c4d28c2329 : TraceRecord {
        attribute :>> elementId = "ALLOC-F-4100-01-4100";
        attribute :>> sourceFile = "Rail_MBSE_Function_Interface_v1_final.xlsx";
        attribute :>> sourceSheet = "Function_Allocation";
        attribute :>> sourceRow = 33;
    }
    item trace_afcf7491815ee06c : TraceRecord {
        attribute :>> elementId = "ALLOC-F-4110-01-4110";
        attribute :>> sourceFile = "Rail_MBSE_Function_Interface_v1_final.xlsx";
        attribute :>> sourceSheet = "Function_Allocation";
        attribute :>> sourceRow = 34;
    }
    item trace_e601f3196e8354a0 : TraceRecord {
        attribute :>> elementId = "ALLOC-F-4111-01-4111";
        attribute :>> sourceFile = "Rail_MBSE_Function_Interface_v1_final.xlsx";
        attribute :>> sourceSheet = "Function_Allocation";
        attribute :>> sourceRow = 35;
    }
    item trace_c67295ad7b4f9d5a : TraceRecord {
        attribute :>> elementId = "ALLOC-F-411C-01-411C";
        attribute :>> sourceFile = "Rail_MBSE_Function_Interface_v1_final.xlsx";
        attribute :>> sourceSheet = "Function_Allocation";
        attribute :>> sourceRow = 36;
    }
    item trace_31e03bbbcec8e078 : TraceRecord {
        attribute :>> elementId = "ALLOC-F-411C-02-411C";
        attribute :>> sourceFile = "Rail_MBSE_Function_Interface_v1_final.xlsx";
        attribute :>> sourceSheet = "Function_Allocation";
        attribute :>> sourceRow = 37;
    }
    item trace_c3d74e289b7683fb : TraceRecord {
        attribute :>> elementId = "ALLOC-F-4200-01-4200";
        attribute :>> sourceFile = "Rail_MBSE_Function_Interface_v1_final.xlsx";
        attribute :>> sourceSheet = "Function_Allocation";
        attribute :>> sourceRow = 38;
    }
    item trace_de5aa350d745991d : TraceRecord {
        attribute :>> elementId = "ALLOC-F-4210-01-4210";
        attribute :>> sourceFile = "Rail_MBSE_Function_Interface_v1_final.xlsx";
        attribute :>> sourceSheet = "Function_Allocation";
        attribute :>> sourceRow = 39;
    }
    item trace_e338b02c1cfbc1d4 : TraceRecord {
        attribute :>> elementId = "ALLOC-F-4211-01-4211";
        attribute :>> sourceFile = "Rail_MBSE_Function_Interface_v1_final.xlsx";
        attribute :>> sourceSheet = "Function_Allocation";
        attribute :>> sourceRow = 40;
    }
    item trace_6915055cc8326740 : TraceRecord {
        attribute :>> elementId = "ALLOC-F-4212-01-4212";
        attribute :>> sourceFile = "Rail_MBSE_Function_Interface_v1_final.xlsx";
        attribute :>> sourceSheet = "Function_Allocation";
        attribute :>> sourceRow = 41;
    }
    item trace_93810c1c4184b3d2 : TraceRecord {
        attribute :>> elementId = "ALLOC-F-4230-01-4230";
        attribute :>> sourceFile = "Rail_MBSE_Function_Interface_v1_final.xlsx";
        attribute :>> sourceSheet = "Function_Allocation";
        attribute :>> sourceRow = 42;
    }
    item trace_f96eecf30587cff0 : TraceRecord {
        attribute :>> elementId = "ALLOC-F-4235-01-4235";
        attribute :>> sourceFile = "Rail_MBSE_Function_Interface_v1_final.xlsx";
        attribute :>> sourceSheet = "Function_Allocation";
        attribute :>> sourceRow = 43;
    }
    item trace_0083d76633cdd69a : TraceRecord {
        attribute :>> elementId = "ALLOC-F-4236-01-4236";
        attribute :>> sourceFile = "Rail_MBSE_Function_Interface_v1_final.xlsx";
        attribute :>> sourceSheet = "Function_Allocation";
        attribute :>> sourceRow = 44;
    }
    item trace_f1fe00fd449fd6a4 : TraceRecord {
        attribute :>> elementId = "ALLOC-F-4238-01-4238";
        attribute :>> sourceFile = "Rail_MBSE_Function_Interface_v1_final.xlsx";
        attribute :>> sourceSheet = "Function_Allocation";
        attribute :>> sourceRow = 45;
    }
    item trace_fa0eb5dc510aabdd : TraceRecord {
        attribute :>> elementId = "ALLOC-F-4238-02-4238";
        attribute :>> sourceFile = "Rail_MBSE_Function_Interface_v1_final.xlsx";
        attribute :>> sourceSheet = "Function_Allocation";
        attribute :>> sourceRow = 46;
    }
    item trace_e8e771d0e86ede3d : TraceRecord {
        attribute :>> elementId = "ALLOC-F-4238-03-4238";
        attribute :>> sourceFile = "Rail_MBSE_Function_Interface_v1_final.xlsx";
        attribute :>> sourceSheet = "Function_Allocation";
        attribute :>> sourceRow = 47;
    }
    item trace_a49d2d5847ad630b : TraceRecord {
        attribute :>> elementId = "ALLOC-F-4239-01-4239";
        attribute :>> sourceFile = "Rail_MBSE_Function_Interface_v1_final.xlsx";
        attribute :>> sourceSheet = "Function_Allocation";
        attribute :>> sourceRow = 48;
    }
    item trace_080c18632627b6d0 : TraceRecord {
        attribute :>> elementId = "ALLOC-F-4239-02-4239";
        attribute :>> sourceFile = "Rail_MBSE_Function_Interface_v1_final.xlsx";
        attribute :>> sourceSheet = "Function_Allocation";
        attribute :>> sourceRow = 49;
    }
    item trace_27d2816a436bbb4e : TraceRecord {
        attribute :>> elementId = "ALLOC-F-4239-03-4239";
        attribute :>> sourceFile = "Rail_MBSE_Function_Interface_v1_final.xlsx";
        attribute :>> sourceSheet = "Function_Allocation";
        attribute :>> sourceRow = 50;
    }
    item trace_285609cee34cdc39 : TraceRecord {
        attribute :>> elementId = "ALLOC-F-4240-01-4240";
        attribute :>> sourceFile = "Rail_MBSE_Function_Interface_v1_final.xlsx";
        attribute :>> sourceSheet = "Function_Allocation";
        attribute :>> sourceRow = 51;
    }
    item trace_213e5428ad09adf4 : TraceRecord {
        attribute :>> elementId = "ALLOC-F-4241-01-4241";
        attribute :>> sourceFile = "Rail_MBSE_Function_Interface_v1_final.xlsx";
        attribute :>> sourceSheet = "Function_Allocation";
        attribute :>> sourceRow = 52;
    }
    item trace_dd7568003ef7d567 : TraceRecord {
        attribute :>> elementId = "ALLOC-F-4241-02-4241";
        attribute :>> sourceFile = "Rail_MBSE_Function_Interface_v1_final.xlsx";
        attribute :>> sourceSheet = "Function_Allocation";
        attribute :>> sourceRow = 53;
    }
    item trace_28a38c238d241ed4 : TraceRecord {
        attribute :>> elementId = "ALLOC-F-4241-03-4241";
        attribute :>> sourceFile = "Rail_MBSE_Function_Interface_v1_final.xlsx";
        attribute :>> sourceSheet = "Function_Allocation";
        attribute :>> sourceRow = 54;
    }
    item trace_5a113c09651e4508 : TraceRecord {
        attribute :>> elementId = "ALLOC-F-4400-01-4400";
        attribute :>> sourceFile = "Rail_MBSE_Function_Interface_v1_final.xlsx";
        attribute :>> sourceSheet = "Function_Allocation";
        attribute :>> sourceRow = 55;
    }
    item trace_fad661927474b53b : TraceRecord {
        attribute :>> elementId = "ALLOC-F-4410-01-4410";
        attribute :>> sourceFile = "Rail_MBSE_Function_Interface_v1_final.xlsx";
        attribute :>> sourceSheet = "Function_Allocation";
        attribute :>> sourceRow = 56;
    }
    item trace_fadff126efd3feee : TraceRecord {
        attribute :>> elementId = "ALLOC-F-4411-01-4411";
        attribute :>> sourceFile = "Rail_MBSE_Function_Interface_v1_final.xlsx";
        attribute :>> sourceSheet = "Function_Allocation";
        attribute :>> sourceRow = 57;
    }
    item trace_6ac4aa264a904402 : TraceRecord {
        attribute :>> elementId = "ALLOC-F-4412-01-4412";
        attribute :>> sourceFile = "Rail_MBSE_Function_Interface_v1_final.xlsx";
        attribute :>> sourceSheet = "Function_Allocation";
        attribute :>> sourceRow = 58;
    }
    item trace_91a029a8ab5ffbb1 : TraceRecord {
        attribute :>> elementId = "ALLOC-F-4413-01-4413";
        attribute :>> sourceFile = "Rail_MBSE_Function_Interface_v1_final.xlsx";
        attribute :>> sourceSheet = "Function_Allocation";
        attribute :>> sourceRow = 59;
    }
    item trace_b04d4efb898315eb : TraceRecord {
        attribute :>> elementId = "ALLOC-F-4500-01-4500";
        attribute :>> sourceFile = "Rail_MBSE_Function_Interface_v1_final.xlsx";
        attribute :>> sourceSheet = "Function_Allocation";
        attribute :>> sourceRow = 60;
    }
    item trace_922192feb8792d48 : TraceRecord {
        attribute :>> elementId = "ALLOC-F-4510-01-4510";
        attribute :>> sourceFile = "Rail_MBSE_Function_Interface_v1_final.xlsx";
        attribute :>> sourceSheet = "Function_Allocation";
        attribute :>> sourceRow = 61;
    }
    item trace_4c7a0e36193cc4c4 : TraceRecord {
        attribute :>> elementId = "ALLOC-F-4511-01-4511";
        attribute :>> sourceFile = "Rail_MBSE_Function_Interface_v1_final.xlsx";
        attribute :>> sourceSheet = "Function_Allocation";
        attribute :>> sourceRow = 62;
    }
    item trace_3c50ce49908e7340 : TraceRecord {
        attribute :>> elementId = "ALLOC-F-4513-01-4513";
        attribute :>> sourceFile = "Rail_MBSE_Function_Interface_v1_final.xlsx";
        attribute :>> sourceSheet = "Function_Allocation";
        attribute :>> sourceRow = 63;
    }
    item trace_34077f7b205c0647 : TraceRecord {
        attribute :>> elementId = "ALLOC-F-4517-01-4517";
        attribute :>> sourceFile = "Rail_MBSE_Function_Interface_v1_final.xlsx";
        attribute :>> sourceSheet = "Function_Allocation";
        attribute :>> sourceRow = 64;
    }
    item trace_e6d5e9ae2ef6c5ea : TraceRecord {
        attribute :>> elementId = "ALLOC-F-4518-01-4518";
        attribute :>> sourceFile = "Rail_MBSE_Function_Interface_v1_final.xlsx";
        attribute :>> sourceSheet = "Function_Allocation";
        attribute :>> sourceRow = 65;
    }
    item trace_efa55508306ba86d : TraceRecord {
        attribute :>> elementId = "ALLOC-F-4518-02-4518";
        attribute :>> sourceFile = "Rail_MBSE_Function_Interface_v1_final.xlsx";
        attribute :>> sourceSheet = "Function_Allocation";
        attribute :>> sourceRow = 66;
    }
    item trace_2fc78e25ae1eece5 : TraceRecord {
        attribute :>> elementId = "ALLOC-F-5000-01-5000";
        attribute :>> sourceFile = "Rail_MBSE_Function_Interface_v1_final.xlsx";
        attribute :>> sourceSheet = "Function_Allocation";
        attribute :>> sourceRow = 67;
    }
    item trace_ff23684005353154 : TraceRecord {
        attribute :>> elementId = "ALLOC-F-5100-01-5100";
        attribute :>> sourceFile = "Rail_MBSE_Function_Interface_v1_final.xlsx";
        attribute :>> sourceSheet = "Function_Allocation";
        attribute :>> sourceRow = 68;
    }
    item trace_91b411308ba95226 : TraceRecord {
        attribute :>> elementId = "ALLOC-F-5110-01-5110";
        attribute :>> sourceFile = "Rail_MBSE_Function_Interface_v1_final.xlsx";
        attribute :>> sourceSheet = "Function_Allocation";
        attribute :>> sourceRow = 69;
    }
    item trace_17227d1aef41fa45 : TraceRecord {
        attribute :>> elementId = "ALLOC-F-5111-01-5111";
        attribute :>> sourceFile = "Rail_MBSE_Function_Interface_v1_final.xlsx";
        attribute :>> sourceSheet = "Function_Allocation";
        attribute :>> sourceRow = 70;
    }
    item trace_428873f64a37364b : TraceRecord {
        attribute :>> elementId = "ALLOC-F-5111-02-5111";
        attribute :>> sourceFile = "Rail_MBSE_Function_Interface_v1_final.xlsx";
        attribute :>> sourceSheet = "Function_Allocation";
        attribute :>> sourceRow = 71;
    }
    item trace_50eda40bd58b6e2d : TraceRecord {
        attribute :>> elementId = "ALLOC-F-5111-03-5111";
        attribute :>> sourceFile = "Rail_MBSE_Function_Interface_v1_final.xlsx";
        attribute :>> sourceSheet = "Function_Allocation";
        attribute :>> sourceRow = 72;
    }
    item trace_35f6f4eee2d30601 : TraceRecord {
        attribute :>> elementId = "ALLOC-F-5111-04-5111";
        attribute :>> sourceFile = "Rail_MBSE_Function_Interface_v1_final.xlsx";
        attribute :>> sourceSheet = "Function_Allocation";
        attribute :>> sourceRow = 73;
    }
    item trace_db52459d55360264 : TraceRecord {
        attribute :>> elementId = "ALLOC-F-5112-01-5112";
        attribute :>> sourceFile = "Rail_MBSE_Function_Interface_v1_final.xlsx";
        attribute :>> sourceSheet = "Function_Allocation";
        attribute :>> sourceRow = 74;
    }
    item trace_61010f42e4ef4dc8 : TraceRecord {
        attribute :>> elementId = "ALLOC-F-5112-02-5112";
        attribute :>> sourceFile = "Rail_MBSE_Function_Interface_v1_final.xlsx";
        attribute :>> sourceSheet = "Function_Allocation";
        attribute :>> sourceRow = 75;
    }
    item trace_eca789bdea0e803a : TraceRecord {
        attribute :>> elementId = "ALLOC-F-5112-03-5112";
        attribute :>> sourceFile = "Rail_MBSE_Function_Interface_v1_final.xlsx";
        attribute :>> sourceSheet = "Function_Allocation";
        attribute :>> sourceRow = 76;
    }
    item trace_4259f201ef951b80 : TraceRecord {
        attribute :>> elementId = "ALLOC-F-5112-04-5112";
        attribute :>> sourceFile = "Rail_MBSE_Function_Interface_v1_final.xlsx";
        attribute :>> sourceSheet = "Function_Allocation";
        attribute :>> sourceRow = 77;
    }
    item trace_2c5787cc8d725138 : TraceRecord {
        attribute :>> elementId = "ALLOC-F-5113-01-5113";
        attribute :>> sourceFile = "Rail_MBSE_Function_Interface_v1_final.xlsx";
        attribute :>> sourceSheet = "Function_Allocation";
        attribute :>> sourceRow = 78;
    }
    item trace_a703a431a2f63056 : TraceRecord {
        attribute :>> elementId = "ALLOC-F-5120-01-5120";
        attribute :>> sourceFile = "Rail_MBSE_Function_Interface_v1_final.xlsx";
        attribute :>> sourceSheet = "Function_Allocation";
        attribute :>> sourceRow = 79;
    }
    item trace_cac0d76bc6cc2adf : TraceRecord {
        attribute :>> elementId = "ALLOC-F-5121-01-5121";
        attribute :>> sourceFile = "Rail_MBSE_Function_Interface_v1_final.xlsx";
        attribute :>> sourceSheet = "Function_Allocation";
        attribute :>> sourceRow = 80;
    }
    item trace_3ac32bc43cdc3538 : TraceRecord {
        attribute :>> elementId = "ALLOC-F-5122-01-5122";
        attribute :>> sourceFile = "Rail_MBSE_Function_Interface_v1_final.xlsx";
        attribute :>> sourceSheet = "Function_Allocation";
        attribute :>> sourceRow = 81;
    }
    item trace_2b1787b98c0c7120 : TraceRecord {
        attribute :>> elementId = "ALLOC-F-5130-01-5130";
        attribute :>> sourceFile = "Rail_MBSE_Function_Interface_v1_final.xlsx";
        attribute :>> sourceSheet = "Function_Allocation";
        attribute :>> sourceRow = 82;
    }
    item trace_e80cb72a76c0e643 : TraceRecord {
        attribute :>> elementId = "ALLOC-F-5131-01-5131";
        attribute :>> sourceFile = "Rail_MBSE_Function_Interface_v1_final.xlsx";
        attribute :>> sourceSheet = "Function_Allocation";
        attribute :>> sourceRow = 83;
    }
    item trace_1960b3b23bbd389a : TraceRecord {
        attribute :>> elementId = "ALLOC-F-5131-02-5131";
        attribute :>> sourceFile = "Rail_MBSE_Function_Interface_v1_final.xlsx";
        attribute :>> sourceSheet = "Function_Allocation";
        attribute :>> sourceRow = 84;
    }
    item trace_ebc73277ae897806 : TraceRecord {
        attribute :>> elementId = "ALLOC-F-5132-01-5132";
        attribute :>> sourceFile = "Rail_MBSE_Function_Interface_v1_final.xlsx";
        attribute :>> sourceSheet = "Function_Allocation";
        attribute :>> sourceRow = 85;
    }
    item trace_f2805675434f3f27 : TraceRecord {
        attribute :>> elementId = "ALLOC-F-5132-02-5132";
        attribute :>> sourceFile = "Rail_MBSE_Function_Interface_v1_final.xlsx";
        attribute :>> sourceSheet = "Function_Allocation";
        attribute :>> sourceRow = 86;
    }
    item trace_6cc1baa46a3482cd : TraceRecord {
        attribute :>> elementId = "ALLOC-F-5133-01-5133";
        attribute :>> sourceFile = "Rail_MBSE_Function_Interface_v1_final.xlsx";
        attribute :>> sourceSheet = "Function_Allocation";
        attribute :>> sourceRow = 87;
    }
    item trace_ea09b0743f744dbd : TraceRecord {
        attribute :>> elementId = "ALLOC-F-5133-02-5133";
        attribute :>> sourceFile = "Rail_MBSE_Function_Interface_v1_final.xlsx";
        attribute :>> sourceSheet = "Function_Allocation";
        attribute :>> sourceRow = 88;
    }
    item trace_1645e7fa18e486b0 : TraceRecord {
        attribute :>> elementId = "ALLOC-F-5133-03-5133";
        attribute :>> sourceFile = "Rail_MBSE_Function_Interface_v1_final.xlsx";
        attribute :>> sourceSheet = "Function_Allocation";
        attribute :>> sourceRow = 89;
    }
    item trace_d953dffd218aef32 : TraceRecord {
        attribute :>> elementId = "ALLOC-F-5140-01-5140";
        attribute :>> sourceFile = "Rail_MBSE_Function_Interface_v1_final.xlsx";
        attribute :>> sourceSheet = "Function_Allocation";
        attribute :>> sourceRow = 90;
    }
    item trace_db48aef78d92c9ef : TraceRecord {
        attribute :>> elementId = "ALLOC-F-5142-01-5142";
        attribute :>> sourceFile = "Rail_MBSE_Function_Interface_v1_final.xlsx";
        attribute :>> sourceSheet = "Function_Allocation";
        attribute :>> sourceRow = 91;
    }
    item trace_2a7785e4f90e6ace : TraceRecord {
        attribute :>> elementId = "ALLOC-F-5142-02-5142";
        attribute :>> sourceFile = "Rail_MBSE_Function_Interface_v1_final.xlsx";
        attribute :>> sourceSheet = "Function_Allocation";
        attribute :>> sourceRow = 92;
    }
    item trace_5fe54d24dfbd2597 : TraceRecord {
        attribute :>> elementId = "ALLOC-F-5145-01-5145";
        attribute :>> sourceFile = "Rail_MBSE_Function_Interface_v1_final.xlsx";
        attribute :>> sourceSheet = "Function_Allocation";
        attribute :>> sourceRow = 93;
    }
    item trace_d8f4b8262cd5639c : TraceRecord {
        attribute :>> elementId = "ALLOC-F-5300-01-5300";
        attribute :>> sourceFile = "Rail_MBSE_Function_Interface_v1_final.xlsx";
        attribute :>> sourceSheet = "Function_Allocation";
        attribute :>> sourceRow = 94;
    }
    item trace_3a67ee3faf05fde4 : TraceRecord {
        attribute :>> elementId = "ALLOC-F-5310-01-5310";
        attribute :>> sourceFile = "Rail_MBSE_Function_Interface_v1_final.xlsx";
        attribute :>> sourceSheet = "Function_Allocation";
        attribute :>> sourceRow = 95;
    }
    item trace_4fc4a8dc1313ab78 : TraceRecord {
        attribute :>> elementId = "ALLOC-F-5311-01-5311";
        attribute :>> sourceFile = "Rail_MBSE_Function_Interface_v1_final.xlsx";
        attribute :>> sourceSheet = "Function_Allocation";
        attribute :>> sourceRow = 96;
    }
    item trace_85d17019c98a0415 : TraceRecord {
        attribute :>> elementId = "ALLOC-F-5311-02-5311";
        attribute :>> sourceFile = "Rail_MBSE_Function_Interface_v1_final.xlsx";
        attribute :>> sourceSheet = "Function_Allocation";
        attribute :>> sourceRow = 97;
    }
    item trace_5258af5f94910080 : TraceRecord {
        attribute :>> elementId = "ALLOC-F-7000-01-7000";
        attribute :>> sourceFile = "Rail_MBSE_Function_Interface_v1_final.xlsx";
        attribute :>> sourceSheet = "Function_Allocation";
        attribute :>> sourceRow = 98;
    }
    item trace_ee9a89677e34e67f : TraceRecord {
        attribute :>> elementId = "ALLOC-F-7100-01-7100";
        attribute :>> sourceFile = "Rail_MBSE_Function_Interface_v1_final.xlsx";
        attribute :>> sourceSheet = "Function_Allocation";
        attribute :>> sourceRow = 99;
    }
    item trace_bf3c38f771fe66a9 : TraceRecord {
        attribute :>> elementId = "ALLOC-F-7120-01-7120";
        attribute :>> sourceFile = "Rail_MBSE_Function_Interface_v1_final.xlsx";
        attribute :>> sourceSheet = "Function_Allocation";
        attribute :>> sourceRow = 100;
    }
    item trace_a25a3a896fa4794c : TraceRecord {
        attribute :>> elementId = "ALLOC-F-7124-01-7124";
        attribute :>> sourceFile = "Rail_MBSE_Function_Interface_v1_final.xlsx";
        attribute :>> sourceSheet = "Function_Allocation";
        attribute :>> sourceRow = 101;
    }
    item trace_a8c0489fb60fe991 : TraceRecord {
        attribute :>> elementId = "ALLOC-F-7130-01-7130";
        attribute :>> sourceFile = "Rail_MBSE_Function_Interface_v1_final.xlsx";
        attribute :>> sourceSheet = "Function_Allocation";
        attribute :>> sourceRow = 102;
    }
    item trace_dd8d05ec2da3bc45 : TraceRecord {
        attribute :>> elementId = "ALLOC-F-7131-01-7131";
        attribute :>> sourceFile = "Rail_MBSE_Function_Interface_v1_final.xlsx";
        attribute :>> sourceSheet = "Function_Allocation";
        attribute :>> sourceRow = 103;
    }
    item trace_0d167017651db12c : TraceRecord {
        attribute :>> elementId = "ALLOC-F-7140-01-7140";
        attribute :>> sourceFile = "Rail_MBSE_Function_Interface_v1_final.xlsx";
        attribute :>> sourceSheet = "Function_Allocation";
        attribute :>> sourceRow = 104;
    }
    item trace_3dc45208662ba348 : TraceRecord {
        attribute :>> elementId = "ALLOC-F-7142-01-7142";
        attribute :>> sourceFile = "Rail_MBSE_Function_Interface_v1_final.xlsx";
        attribute :>> sourceSheet = "Function_Allocation";
        attribute :>> sourceRow = 105;
    }
    item trace_a74186fc29cac026 : TraceRecord {
        attribute :>> elementId = "ALLOC-F-7200-01-7200";
        attribute :>> sourceFile = "Rail_MBSE_Function_Interface_v1_final.xlsx";
        attribute :>> sourceSheet = "Function_Allocation";
        attribute :>> sourceRow = 106;
    }
    item trace_d5647ccd4e63f3e2 : TraceRecord {
        attribute :>> elementId = "ALLOC-F-7210-01-7210";
        attribute :>> sourceFile = "Rail_MBSE_Function_Interface_v1_final.xlsx";
        attribute :>> sourceSheet = "Function_Allocation";
        attribute :>> sourceRow = 107;
    }
    item trace_b282207a0a7c5f5c : TraceRecord {
        attribute :>> elementId = "ALLOC-F-7211-01-7211";
        attribute :>> sourceFile = "Rail_MBSE_Function_Interface_v1_final.xlsx";
        attribute :>> sourceSheet = "Function_Allocation";
        attribute :>> sourceRow = 108;
    }
    item trace_760785ffb5d37493 : TraceRecord {
        attribute :>> elementId = "ALLOC-F-7211-02-7211";
        attribute :>> sourceFile = "Rail_MBSE_Function_Interface_v1_final.xlsx";
        attribute :>> sourceSheet = "Function_Allocation";
        attribute :>> sourceRow = 109;
    }
    item trace_bf679a2b89565713 : TraceRecord {
        attribute :>> elementId = "ALLOC-F-7211-03-7211";
        attribute :>> sourceFile = "Rail_MBSE_Function_Interface_v1_final.xlsx";
        attribute :>> sourceSheet = "Function_Allocation";
        attribute :>> sourceRow = 110;
    }
    item trace_56d9c6940e1c66af : TraceRecord {
        attribute :>> elementId = "ALLOC-F-7211-04-7211";
        attribute :>> sourceFile = "Rail_MBSE_Function_Interface_v1_final.xlsx";
        attribute :>> sourceSheet = "Function_Allocation";
        attribute :>> sourceRow = 111;
    }
    item trace_2729adaf31cb201b : TraceRecord {
        attribute :>> elementId = "ALLOC-F-7213-01-7213";
        attribute :>> sourceFile = "Rail_MBSE_Function_Interface_v1_final.xlsx";
        attribute :>> sourceSheet = "Function_Allocation";
        attribute :>> sourceRow = 112;
    }
    item trace_fa05be30986adefa : TraceRecord {
        attribute :>> elementId = "ALLOC-F-7220-01-7220";
        attribute :>> sourceFile = "Rail_MBSE_Function_Interface_v1_final.xlsx";
        attribute :>> sourceSheet = "Function_Allocation";
        attribute :>> sourceRow = 113;
    }
    item trace_56b7665d73388cf8 : TraceRecord {
        attribute :>> elementId = "ALLOC-F-7222-01-7222";
        attribute :>> sourceFile = "Rail_MBSE_Function_Interface_v1_final.xlsx";
        attribute :>> sourceSheet = "Function_Allocation";
        attribute :>> sourceRow = 114;
    }
    item trace_940f852539244693 : TraceRecord {
        attribute :>> elementId = "ALLOC-F-7223-01-7223";
        attribute :>> sourceFile = "Rail_MBSE_Function_Interface_v1_final.xlsx";
        attribute :>> sourceSheet = "Function_Allocation";
        attribute :>> sourceRow = 115;
    }
    item trace_a51c96446c29896b : TraceRecord {
        attribute :>> elementId = "ALLOC-F-7224-01-7224";
        attribute :>> sourceFile = "Rail_MBSE_Function_Interface_v1_final.xlsx";
        attribute :>> sourceSheet = "Function_Allocation";
        attribute :>> sourceRow = 116;
    }
    item trace_1419efd3d2faa8c6 : TraceRecord {
        attribute :>> elementId = "ALLOC-F-7225-01-7225";
        attribute :>> sourceFile = "Rail_MBSE_Function_Interface_v1_final.xlsx";
        attribute :>> sourceSheet = "Function_Allocation";
        attribute :>> sourceRow = 117;
    }
    item trace_d455525c8fdd7afa : TraceRecord {
        attribute :>> elementId = "ALLOC-F-7226-01-7226";
        attribute :>> sourceFile = "Rail_MBSE_Function_Interface_v1_final.xlsx";
        attribute :>> sourceSheet = "Function_Allocation";
        attribute :>> sourceRow = 118;
    }
    item trace_ef0374186127464e : TraceRecord {
        attribute :>> elementId = "ALLOC-F-7227-01-7227";
        attribute :>> sourceFile = "Rail_MBSE_Function_Interface_v1_final.xlsx";
        attribute :>> sourceSheet = "Function_Allocation";
        attribute :>> sourceRow = 119;
    }
    item trace_ba581755b20acfa4 : TraceRecord {
        attribute :>> elementId = "ALLOC-F-7228-01-7228";
        attribute :>> sourceFile = "Rail_MBSE_Function_Interface_v1_final.xlsx";
        attribute :>> sourceSheet = "Function_Allocation";
        attribute :>> sourceRow = 120;
    }
    item trace_8ac0ae60469a4a51 : TraceRecord {
        attribute :>> elementId = "ALLOC-F-7229-01-7229";
        attribute :>> sourceFile = "Rail_MBSE_Function_Interface_v1_final.xlsx";
        attribute :>> sourceSheet = "Function_Allocation";
        attribute :>> sourceRow = 121;
    }
    item trace_36d9d7b7413e337b : TraceRecord {
        attribute :>> elementId = "ALLOC-F-722A-01-722A";
        attribute :>> sourceFile = "Rail_MBSE_Function_Interface_v1_final.xlsx";
        attribute :>> sourceSheet = "Function_Allocation";
        attribute :>> sourceRow = 122;
    }
    item trace_fb9a236e5eb13a3c : TraceRecord {
        attribute :>> elementId = "ALLOC-F-722B-01-722B";
        attribute :>> sourceFile = "Rail_MBSE_Function_Interface_v1_final.xlsx";
        attribute :>> sourceSheet = "Function_Allocation";
        attribute :>> sourceRow = 123;
    }
    item trace_d99e02ab5ce8e370 : TraceRecord {
        attribute :>> elementId = "ALLOC-F-722C-01-722C";
        attribute :>> sourceFile = "Rail_MBSE_Function_Interface_v1_final.xlsx";
        attribute :>> sourceSheet = "Function_Allocation";
        attribute :>> sourceRow = 124;
    }
    item trace_9affc9b2c12f13bf : TraceRecord {
        attribute :>> elementId = "ALLOC-F-7250-01-7250";
        attribute :>> sourceFile = "Rail_MBSE_Function_Interface_v1_final.xlsx";
        attribute :>> sourceSheet = "Function_Allocation";
        attribute :>> sourceRow = 125;
    }
    item trace_bb1622b6b5954b83 : TraceRecord {
        attribute :>> elementId = "ALLOC-F-7252-01-7252";
        attribute :>> sourceFile = "Rail_MBSE_Function_Interface_v1_final.xlsx";
        attribute :>> sourceSheet = "Function_Allocation";
        attribute :>> sourceRow = 126;
    }
    item trace_01e7ffe1e62218df : TraceRecord {
        attribute :>> elementId = "ALLOC-F-7254-01-7254";
        attribute :>> sourceFile = "Rail_MBSE_Function_Interface_v1_final.xlsx";
        attribute :>> sourceSheet = "Function_Allocation";
        attribute :>> sourceRow = 127;
    }
    item trace_626f75f5d31efa79 : TraceRecord {
        attribute :>> elementId = "ALLOC-F-7255-01-7255";
        attribute :>> sourceFile = "Rail_MBSE_Function_Interface_v1_final.xlsx";
        attribute :>> sourceSheet = "Function_Allocation";
        attribute :>> sourceRow = 128;
    }
    item trace_fdd93039c7186224 : TraceRecord {
        attribute :>> elementId = "ALLOC-F-7280-01-7280";
        attribute :>> sourceFile = "Rail_MBSE_Function_Interface_v1_final.xlsx";
        attribute :>> sourceSheet = "Function_Allocation";
        attribute :>> sourceRow = 129;
    }
    item trace_fa48380d4baa007f : TraceRecord {
        attribute :>> elementId = "ALLOC-F-7281-01-7281";
        attribute :>> sourceFile = "Rail_MBSE_Function_Interface_v1_final.xlsx";
        attribute :>> sourceSheet = "Function_Allocation";
        attribute :>> sourceRow = 130;
    }
    item trace_a3d3eadaddaaf9f7 : TraceRecord {
        attribute :>> elementId = "ALLOC-F-7284-01-7284";
        attribute :>> sourceFile = "Rail_MBSE_Function_Interface_v1_final.xlsx";
        attribute :>> sourceSheet = "Function_Allocation";
        attribute :>> sourceRow = 131;
    }
    item trace_e38025e29e248d62 : TraceRecord {
        attribute :>> elementId = "ALLOC-F-7285-01-7285";
        attribute :>> sourceFile = "Rail_MBSE_Function_Interface_v1_final.xlsx";
        attribute :>> sourceSheet = "Function_Allocation";
        attribute :>> sourceRow = 132;
    }
    item trace_ec89cacefd8c907d : TraceRecord {
        attribute :>> elementId = "ALLOC-F-8000-01-8000";
        attribute :>> sourceFile = "Rail_MBSE_Function_Interface_v1_final.xlsx";
        attribute :>> sourceSheet = "Function_Allocation";
        attribute :>> sourceRow = 133;
    }
    item trace_1947095cc301a143 : TraceRecord {
        attribute :>> elementId = "ALLOC-F-8100-01-8100";
        attribute :>> sourceFile = "Rail_MBSE_Function_Interface_v1_final.xlsx";
        attribute :>> sourceSheet = "Function_Allocation";
        attribute :>> sourceRow = 134;
    }
    item trace_3c37175b8ec33135 : TraceRecord {
        attribute :>> elementId = "ALLOC-F-8120-01-8120";
        attribute :>> sourceFile = "Rail_MBSE_Function_Interface_v1_final.xlsx";
        attribute :>> sourceSheet = "Function_Allocation";
        attribute :>> sourceRow = 135;
    }
    item trace_77a577e4104c8b4d : TraceRecord {
        attribute :>> elementId = "ALLOC-F-8121-01-8121";
        attribute :>> sourceFile = "Rail_MBSE_Function_Interface_v1_final.xlsx";
        attribute :>> sourceSheet = "Function_Allocation";
        attribute :>> sourceRow = 136;
    }
    item trace_afbe6ba619afc880 : TraceRecord {
        attribute :>> elementId = "ALLOC-F-8121-02-8121";
        attribute :>> sourceFile = "Rail_MBSE_Function_Interface_v1_final.xlsx";
        attribute :>> sourceSheet = "Function_Allocation";
        attribute :>> sourceRow = 137;
    }
    item trace_c00cf398d0139206 : TraceRecord {
        attribute :>> elementId = "ALLOC-F-8121-03-8121";
        attribute :>> sourceFile = "Rail_MBSE_Function_Interface_v1_final.xlsx";
        attribute :>> sourceSheet = "Function_Allocation";
        attribute :>> sourceRow = 138;
    }
    item trace_82844142513f06a2 : TraceRecord {
        attribute :>> elementId = "ALLOC-F-8122-01-8122";
        attribute :>> sourceFile = "Rail_MBSE_Function_Interface_v1_final.xlsx";
        attribute :>> sourceSheet = "Function_Allocation";
        attribute :>> sourceRow = 139;
    }
    item trace_72dd55e4ac1c9774 : TraceRecord {
        attribute :>> elementId = "ALLOC-F-8122-02-8122";
        attribute :>> sourceFile = "Rail_MBSE_Function_Interface_v1_final.xlsx";
        attribute :>> sourceSheet = "Function_Allocation";
        attribute :>> sourceRow = 140;
    }
    item trace_9662be898b55a754 : TraceRecord {
        attribute :>> elementId = "ALLOC-F-8122-03-8122";
        attribute :>> sourceFile = "Rail_MBSE_Function_Interface_v1_final.xlsx";
        attribute :>> sourceSheet = "Function_Allocation";
        attribute :>> sourceRow = 141;
    }
    item trace_5ee9be4977ed312c : TraceRecord {
        attribute :>> elementId = "ALLOC-F-8122-04-8122";
        attribute :>> sourceFile = "Rail_MBSE_Function_Interface_v1_final.xlsx";
        attribute :>> sourceSheet = "Function_Allocation";
        attribute :>> sourceRow = 142;
    }
    item trace_421cb91fa09e21aa : TraceRecord {
        attribute :>> elementId = "ALLOC-F-8122-05-8122";
        attribute :>> sourceFile = "Rail_MBSE_Function_Interface_v1_final.xlsx";
        attribute :>> sourceSheet = "Function_Allocation";
        attribute :>> sourceRow = 143;
    }
    item trace_c8ed4727b369278e : TraceRecord {
        attribute :>> elementId = "ALLOC-F-8125-01-8125";
        attribute :>> sourceFile = "Rail_MBSE_Function_Interface_v1_final.xlsx";
        attribute :>> sourceSheet = "Function_Allocation";
        attribute :>> sourceRow = 144;
    }
    item trace_e19b9213748541d5 : TraceRecord {
        attribute :>> elementId = "ALLOC-F-8125-02-8125";
        attribute :>> sourceFile = "Rail_MBSE_Function_Interface_v1_final.xlsx";
        attribute :>> sourceSheet = "Function_Allocation";
        attribute :>> sourceRow = 145;
    }
    item trace_c5bae9b2e3594094 : TraceRecord {
        attribute :>> elementId = "ALLOC-F-8125-03-8125";
        attribute :>> sourceFile = "Rail_MBSE_Function_Interface_v1_final.xlsx";
        attribute :>> sourceSheet = "Function_Allocation";
        attribute :>> sourceRow = 146;
    }
    item trace_eac2779368037d4e : TraceRecord {
        attribute :>> elementId = "ALLOC-F-8125-04-8125";
        attribute :>> sourceFile = "Rail_MBSE_Function_Interface_v1_final.xlsx";
        attribute :>> sourceSheet = "Function_Allocation";
        attribute :>> sourceRow = 147;
    }
    item trace_c1c6ee91ba5d6bc7 : TraceRecord {
        attribute :>> elementId = "ALLOC-F-8127-01-8127";
        attribute :>> sourceFile = "Rail_MBSE_Function_Interface_v1_final.xlsx";
        attribute :>> sourceSheet = "Function_Allocation";
        attribute :>> sourceRow = 148;
    }
    item trace_a019eb12387639ca : TraceRecord {
        attribute :>> elementId = "ALLOC-F-8127-02-8127";
        attribute :>> sourceFile = "Rail_MBSE_Function_Interface_v1_final.xlsx";
        attribute :>> sourceSheet = "Function_Allocation";
        attribute :>> sourceRow = 149;
    }
    item trace_5bb7be8e2ea80da4 : TraceRecord {
        attribute :>> elementId = "ALLOC-F-8128-01-8128";
        attribute :>> sourceFile = "Rail_MBSE_Function_Interface_v1_final.xlsx";
        attribute :>> sourceSheet = "Function_Allocation";
        attribute :>> sourceRow = 150;
    }
    item trace_3ce7d3fefab795d1 : TraceRecord {
        attribute :>> elementId = "ALLOC-F-8128-02-8128";
        attribute :>> sourceFile = "Rail_MBSE_Function_Interface_v1_final.xlsx";
        attribute :>> sourceSheet = "Function_Allocation";
        attribute :>> sourceRow = 151;
    }
    item trace_9d7b86ea40aaea43 : TraceRecord {
        attribute :>> elementId = "ALLOC-F-8128-03-8128";
        attribute :>> sourceFile = "Rail_MBSE_Function_Interface_v1_final.xlsx";
        attribute :>> sourceSheet = "Function_Allocation";
        attribute :>> sourceRow = 152;
    }
    item trace_7d7eef4e39336172 : TraceRecord {
        attribute :>> elementId = "ALLOC-F-8150-01-8150";
        attribute :>> sourceFile = "Rail_MBSE_Function_Interface_v1_final.xlsx";
        attribute :>> sourceSheet = "Function_Allocation";
        attribute :>> sourceRow = 153;
    }
    item trace_78bb89a9764e0e5b : TraceRecord {
        attribute :>> elementId = "ALLOC-F-8151-01-8151";
        attribute :>> sourceFile = "Rail_MBSE_Function_Interface_v1_final.xlsx";
        attribute :>> sourceSheet = "Function_Allocation";
        attribute :>> sourceRow = 154;
    }
    item trace_670320ab26224f92 : TraceRecord {
        attribute :>> elementId = "ALLOC-F-8151-02-8151";
        attribute :>> sourceFile = "Rail_MBSE_Function_Interface_v1_final.xlsx";
        attribute :>> sourceSheet = "Function_Allocation";
        attribute :>> sourceRow = 155;
    }
    item trace_cef7a2271f8381c4 : TraceRecord {
        attribute :>> elementId = "ALLOC-F-8152-01-8152";
        attribute :>> sourceFile = "Rail_MBSE_Function_Interface_v1_final.xlsx";
        attribute :>> sourceSheet = "Function_Allocation";
        attribute :>> sourceRow = 156;
    }
    item trace_f56fbf149a4ef067 : TraceRecord {
        attribute :>> elementId = "ALLOC-F-8152-02-8152";
        attribute :>> sourceFile = "Rail_MBSE_Function_Interface_v1_final.xlsx";
        attribute :>> sourceSheet = "Function_Allocation";
        attribute :>> sourceRow = 157;
    }
    item trace_2698d1a40729b5e0 : TraceRecord {
        attribute :>> elementId = "ALLOC-F-8154-01-8154";
        attribute :>> sourceFile = "Rail_MBSE_Function_Interface_v1_final.xlsx";
        attribute :>> sourceSheet = "Function_Allocation";
        attribute :>> sourceRow = 158;
    }
    item trace_343a85677059a6a6 : TraceRecord {
        attribute :>> elementId = "ALLOC-F-8154-02-8154";
        attribute :>> sourceFile = "Rail_MBSE_Function_Interface_v1_final.xlsx";
        attribute :>> sourceSheet = "Function_Allocation";
        attribute :>> sourceRow = 159;
    }
    item trace_918b73d90fb0c101 : TraceRecord {
        attribute :>> elementId = "ALLOC-F-8160-01-8160";
        attribute :>> sourceFile = "Rail_MBSE_Function_Interface_v1_final.xlsx";
        attribute :>> sourceSheet = "Function_Allocation";
        attribute :>> sourceRow = 160;
    }
    item trace_ac81b05ffe2d8e58 : TraceRecord {
        attribute :>> elementId = "ALLOC-F-8166-01-8166";
        attribute :>> sourceFile = "Rail_MBSE_Function_Interface_v1_final.xlsx";
        attribute :>> sourceSheet = "Function_Allocation";
        attribute :>> sourceRow = 161;
    }
    item trace_c3e1c99fddb0a132 : TraceRecord {
        attribute :>> elementId = "ALLOC-F-8166-02-8166";
        attribute :>> sourceFile = "Rail_MBSE_Function_Interface_v1_final.xlsx";
        attribute :>> sourceSheet = "Function_Allocation";
        attribute :>> sourceRow = 162;
    }
    item trace_95ea738db720b91a : TraceRecord {
        attribute :>> elementId = "ALLOC-F-8166-03-8166";
        attribute :>> sourceFile = "Rail_MBSE_Function_Interface_v1_final.xlsx";
        attribute :>> sourceSheet = "Function_Allocation";
        attribute :>> sourceRow = 163;
    }
    item trace_5a915a7e8d83a73c : TraceRecord {
        attribute :>> elementId = "ALLOC-F-8166-04-8166";
        attribute :>> sourceFile = "Rail_MBSE_Function_Interface_v1_final.xlsx";
        attribute :>> sourceSheet = "Function_Allocation";
        attribute :>> sourceRow = 164;
    }
    item trace_855ef75106addfa4 : TraceRecord {
        attribute :>> elementId = "ALLOC-F-D000-01-D000";
        attribute :>> sourceFile = "Rail_MBSE_Function_Interface_v1_final.xlsx";
        attribute :>> sourceSheet = "Function_Allocation";
        attribute :>> sourceRow = 165;
    }
    item trace_c85e99e1b6ca5992 : TraceRecord {
        attribute :>> elementId = "ALLOC-F-D100-01-D100";
        attribute :>> sourceFile = "Rail_MBSE_Function_Interface_v1_final.xlsx";
        attribute :>> sourceSheet = "Function_Allocation";
        attribute :>> sourceRow = 166;
    }
    item trace_6730ee4677e3c946 : TraceRecord {
        attribute :>> elementId = "ALLOC-F-D110-01-D110";
        attribute :>> sourceFile = "Rail_MBSE_Function_Interface_v1_final.xlsx";
        attribute :>> sourceSheet = "Function_Allocation";
        attribute :>> sourceRow = 167;
    }
    item trace_5f92604b32561ac7 : TraceRecord {
        attribute :>> elementId = "ALLOC-F-D112-01-D112";
        attribute :>> sourceFile = "Rail_MBSE_Function_Interface_v1_final.xlsx";
        attribute :>> sourceSheet = "Function_Allocation";
        attribute :>> sourceRow = 168;
    }
    item trace_28d894681251009f : TraceRecord {
        attribute :>> elementId = "ALLOC-F-D113-01-D113";
        attribute :>> sourceFile = "Rail_MBSE_Function_Interface_v1_final.xlsx";
        attribute :>> sourceSheet = "Function_Allocation";
        attribute :>> sourceRow = 169;
    }
    item trace_5dc460e1d29863de : TraceRecord {
        attribute :>> elementId = "ALLOC-F-D114-01-D114";
        attribute :>> sourceFile = "Rail_MBSE_Function_Interface_v1_final.xlsx";
        attribute :>> sourceSheet = "Function_Allocation";
        attribute :>> sourceRow = 170;
    }
    item trace_e7eae2565b0e0b82 : TraceRecord {
        attribute :>> elementId = "ALLOC-F-D120-01-D120";
        attribute :>> sourceFile = "Rail_MBSE_Function_Interface_v1_final.xlsx";
        attribute :>> sourceSheet = "Function_Allocation";
        attribute :>> sourceRow = 171;
    }
    item trace_0f6c15040fee12e5 : TraceRecord {
        attribute :>> elementId = "ALLOC-F-D121-01-D121";
        attribute :>> sourceFile = "Rail_MBSE_Function_Interface_v1_final.xlsx";
        attribute :>> sourceSheet = "Function_Allocation";
        attribute :>> sourceRow = 172;
    }
    item trace_13cdcd8eaed514b4 : TraceRecord {
        attribute :>> elementId = "ALLOC-F-D130-01-D130";
        attribute :>> sourceFile = "Rail_MBSE_Function_Interface_v1_final.xlsx";
        attribute :>> sourceSheet = "Function_Allocation";
        attribute :>> sourceRow = 173;
    }
    item trace_ca18bcb859a9ad5b : TraceRecord {
        attribute :>> elementId = "ALLOC-F-D13B-01-D13B";
        attribute :>> sourceFile = "Rail_MBSE_Function_Interface_v1_final.xlsx";
        attribute :>> sourceSheet = "Function_Allocation";
        attribute :>> sourceRow = 174;
    }
    item trace_c5206232b127eced : TraceRecord {
        attribute :>> elementId = "ALLOC-F-E000-01-E000";
        attribute :>> sourceFile = "Rail_MBSE_Function_Interface_v1_final.xlsx";
        attribute :>> sourceSheet = "Function_Allocation";
        attribute :>> sourceRow = 175;
    }
    item trace_41ef7f950b9a2e32 : TraceRecord {
        attribute :>> elementId = "ALLOC-F-E100-01-E100";
        attribute :>> sourceFile = "Rail_MBSE_Function_Interface_v1_final.xlsx";
        attribute :>> sourceSheet = "Function_Allocation";
        attribute :>> sourceRow = 176;
    }
    item trace_173996fc330035b2 : TraceRecord {
        attribute :>> elementId = "ALLOC-F-X000-01-X000";
        attribute :>> sourceFile = "Rail_MBSE_Function_Interface_v1_final.xlsx";
        attribute :>> sourceSheet = "Function_Allocation";
        attribute :>> sourceRow = 177;
    }
    item trace_b64195c15ab9b697 : TraceRecord {
        attribute :>> elementId = "ALLOC-F-X100-01-X100";
        attribute :>> sourceFile = "Rail_MBSE_Function_Interface_v1_final.xlsx";
        attribute :>> sourceSheet = "Function_Allocation";
        attribute :>> sourceRow = 178;
    }
    item trace_fd0224180dfcebe2 : TraceRecord {
        attribute :>> elementId = "ALLOC-F-X110-01-X110";
        attribute :>> sourceFile = "Rail_MBSE_Function_Interface_v1_final.xlsx";
        attribute :>> sourceSheet = "Function_Allocation";
        attribute :>> sourceRow = 179;
    }
    item trace_b0a891764b3b1b1c : TraceRecord {
        attribute :>> elementId = "ALLOC-F-X111-01-X111";
        attribute :>> sourceFile = "Rail_MBSE_Function_Interface_v1_final.xlsx";
        attribute :>> sourceSheet = "Function_Allocation";
        attribute :>> sourceRow = 180;
    }
    item trace_49edec8198eace31 : TraceRecord {
        attribute :>> elementId = "ALLOC-F-X111-02-X111";
        attribute :>> sourceFile = "Rail_MBSE_Function_Interface_v1_final.xlsx";
        attribute :>> sourceSheet = "Function_Allocation";
        attribute :>> sourceRow = 181;
    }
    item trace_5565411f9fa0dbc0 : TraceRecord {
        attribute :>> elementId = "ALLOC-F-X112-01-X112";
        attribute :>> sourceFile = "Rail_MBSE_Function_Interface_v1_final.xlsx";
        attribute :>> sourceSheet = "Function_Allocation";
        attribute :>> sourceRow = 182;
    }
    item trace_6f8bb736c4500150 : TraceRecord {
        attribute :>> elementId = "ALLOC-F-X112-02-X112";
        attribute :>> sourceFile = "Rail_MBSE_Function_Interface_v1_final.xlsx";
        attribute :>> sourceSheet = "Function_Allocation";
        attribute :>> sourceRow = 183;
    }
    item trace_51f2603861384457 : TraceRecord {
        attribute :>> elementId = "ALLOC-F-X112-03-X112";
        attribute :>> sourceFile = "Rail_MBSE_Function_Interface_v1_final.xlsx";
        attribute :>> sourceSheet = "Function_Allocation";
        attribute :>> sourceRow = 184;
    }
    item trace_a94829adf3b8e486 : TraceRecord {
        attribute :>> elementId = "ALLOC-F-X113-01-X113";
        attribute :>> sourceFile = "Rail_MBSE_Function_Interface_v1_final.xlsx";
        attribute :>> sourceSheet = "Function_Allocation";
        attribute :>> sourceRow = 185;
    }
    item trace_49ca236457caba65 : TraceRecord {
        attribute :>> elementId = "ALLOC-F-X120-01-X120";
        attribute :>> sourceFile = "Rail_MBSE_Function_Interface_v1_final.xlsx";
        attribute :>> sourceSheet = "Function_Allocation";
        attribute :>> sourceRow = 186;
    }
    item trace_32772cafdda17364 : TraceRecord {
        attribute :>> elementId = "ALLOC-F-X121-01-X121";
        attribute :>> sourceFile = "Rail_MBSE_Function_Interface_v1_final.xlsx";
        attribute :>> sourceSheet = "Function_Allocation";
        attribute :>> sourceRow = 187;
    }
    item trace_83febb71db509308 : TraceRecord {
        attribute :>> elementId = "ALLOC-F-X121-02-X121";
        attribute :>> sourceFile = "Rail_MBSE_Function_Interface_v1_final.xlsx";
        attribute :>> sourceSheet = "Function_Allocation";
        attribute :>> sourceRow = 188;
    }
    item trace_066044a3d3478ea8 : TraceRecord {
        attribute :>> elementId = "ALLOC-F-X122-01-X122";
        attribute :>> sourceFile = "Rail_MBSE_Function_Interface_v1_final.xlsx";
        attribute :>> sourceSheet = "Function_Allocation";
        attribute :>> sourceRow = 189;
    }
    item trace_6eb8e7d826be0aaf : TraceRecord {
        attribute :>> elementId = "ALLOC-F-X123-01-X123";
        attribute :>> sourceFile = "Rail_MBSE_Function_Interface_v1_final.xlsx";
        attribute :>> sourceSheet = "Function_Allocation";
        attribute :>> sourceRow = 190;
    }
    item trace_5ce91d0f32df3cc8 : TraceRecord {
        attribute :>> elementId = "ALLOC-F-X124-01-X124";
        attribute :>> sourceFile = "Rail_MBSE_Function_Interface_v1_final.xlsx";
        attribute :>> sourceSheet = "Function_Allocation";
        attribute :>> sourceRow = 191;
    }
    item trace_c9ce9de6dd1d858d : TraceRecord {
        attribute :>> elementId = "ALLOC-F-X130-01-X130";
        attribute :>> sourceFile = "Rail_MBSE_Function_Interface_v1_final.xlsx";
        attribute :>> sourceSheet = "Function_Allocation";
        attribute :>> sourceRow = 192;
    }
    item trace_c20bea20fe5b2fa8 : TraceRecord {
        attribute :>> elementId = "ALLOC-F-X131-01-X131";
        attribute :>> sourceFile = "Rail_MBSE_Function_Interface_v1_final.xlsx";
        attribute :>> sourceSheet = "Function_Allocation";
        attribute :>> sourceRow = 193;
    }
    item trace_1a76350f09d3ac4d : TraceRecord {
        attribute :>> elementId = "ALLOC-F-X132-01-X132";
        attribute :>> sourceFile = "Rail_MBSE_Function_Interface_v1_final.xlsx";
        attribute :>> sourceSheet = "Function_Allocation";
        attribute :>> sourceRow = 194;
    }
    item trace_7198ab3c39c6a3ba : TraceRecord {
        attribute :>> elementId = "ALLOC-F-X133-01-X133";
        attribute :>> sourceFile = "Rail_MBSE_Function_Interface_v1_final.xlsx";
        attribute :>> sourceSheet = "Function_Allocation";
        attribute :>> sourceRow = 195;
    }
    item trace_fe34f22ad05b30d4 : TraceRecord {
        attribute :>> elementId = "CG-002543DBE0F9A7FBC2A3FDD3";
        attribute :>> sourceFile = "Rail_MBSE_Function_Interface_v1_final.xlsx";
        attribute :>> sourceSheet = "Connection";
        attribute :>> sourceRow = 5;
    }
    item trace_1f13f58edef95614 : TraceRecord {
        attribute :>> elementId = "CG-071B7693DAFA8B87ADA0A61E";
        attribute :>> sourceFile = "Rail_MBSE_Function_Interface_v1_final.xlsx";
        attribute :>> sourceSheet = "Connection";
        attribute :>> sourceRow = 6;
    }
    item trace_5cf50e16b01ff7c4 : TraceRecord {
        attribute :>> elementId = "CG-07AF42BFA3927EF22F7BDDE7";
        attribute :>> sourceFile = "Rail_MBSE_Function_Interface_v1_final.xlsx";
        attribute :>> sourceSheet = "Connection";
        attribute :>> sourceRow = 7;
    }
    item trace_593dfaa321757bcf : TraceRecord {
        attribute :>> elementId = "CG-08375F15DCE75E45D4C45CE8";
        attribute :>> sourceFile = "Rail_MBSE_Function_Interface_v1_final.xlsx";
        attribute :>> sourceSheet = "Connection";
        attribute :>> sourceRow = 8;
    }
    item trace_4e2cf3c2375c8444 : TraceRecord {
        attribute :>> elementId = "CG-093EFCE58F3AB220CFEC48AC";
        attribute :>> sourceFile = "Rail_MBSE_Function_Interface_v1_final.xlsx";
        attribute :>> sourceSheet = "Connection";
        attribute :>> sourceRow = 9;
    }
    item trace_5c8a60d7f5cf3f9a : TraceRecord {
        attribute :>> elementId = "CG-0B7698B3C627150EF560B4B0";
        attribute :>> sourceFile = "Rail_MBSE_Function_Interface_v1_final.xlsx";
        attribute :>> sourceSheet = "Connection";
        attribute :>> sourceRow = 10;
    }
    item trace_ee4c33a1ac27ede1 : TraceRecord {
        attribute :>> elementId = "CG-0D68248E62957CCB92C5A2A5";
        attribute :>> sourceFile = "Rail_MBSE_Function_Interface_v1_final.xlsx";
        attribute :>> sourceSheet = "Connection";
        attribute :>> sourceRow = 11;
    }
    item trace_5689e51f444018db : TraceRecord {
        attribute :>> elementId = "CG-1102EBD35D52A38B96D5D2E7";
        attribute :>> sourceFile = "Rail_MBSE_Function_Interface_v1_final.xlsx";
        attribute :>> sourceSheet = "Connection";
        attribute :>> sourceRow = 12;
    }
    item trace_788c5f9c41b43b3e : TraceRecord {
        attribute :>> elementId = "CG-117A3F0E6C8FF8FF0013A46B";
        attribute :>> sourceFile = "Rail_MBSE_Function_Interface_v1_final.xlsx";
        attribute :>> sourceSheet = "Connection";
        attribute :>> sourceRow = 13;
    }
    item trace_a8f9ecd569728c67 : TraceRecord {
        attribute :>> elementId = "CG-118F2C2B84D1D301C7BE63F8";
        attribute :>> sourceFile = "Rail_MBSE_Function_Interface_v1_final.xlsx";
        attribute :>> sourceSheet = "Connection";
        attribute :>> sourceRow = 14;
    }
    item trace_ff8c25103e1695ed : TraceRecord {
        attribute :>> elementId = "CG-121266057FF9E69E8769A5CA";
        attribute :>> sourceFile = "Rail_MBSE_Function_Interface_v1_final.xlsx";
        attribute :>> sourceSheet = "Connection";
        attribute :>> sourceRow = 15;
    }
    item trace_5b6196d9aa4415d3 : TraceRecord {
        attribute :>> elementId = "CG-13AAF69570338FD5B6C27BC3";
        attribute :>> sourceFile = "Rail_MBSE_Function_Interface_v1_final.xlsx";
        attribute :>> sourceSheet = "Connection";
        attribute :>> sourceRow = 16;
    }
    item trace_d2de8ff579d8755f : TraceRecord {
        attribute :>> elementId = "CG-14318213721CBD91F198F77B";
        attribute :>> sourceFile = "Rail_MBSE_Function_Interface_v1_final.xlsx";
        attribute :>> sourceSheet = "Connection";
        attribute :>> sourceRow = 17;
    }
    item trace_2ef3a704b5ac019e : TraceRecord {
        attribute :>> elementId = "CG-14D79A46EA4824EAC69F2DCF";
        attribute :>> sourceFile = "Rail_MBSE_Function_Interface_v1_final.xlsx";
        attribute :>> sourceSheet = "Connection";
        attribute :>> sourceRow = 18;
    }
    item trace_c4276d8445d1262a : TraceRecord {
        attribute :>> elementId = "CG-166B9301CD54035D82DA7711";
        attribute :>> sourceFile = "Rail_MBSE_Function_Interface_v1_final.xlsx";
        attribute :>> sourceSheet = "Connection";
        attribute :>> sourceRow = 19;
    }
    item trace_0d2c9500368b1db0 : TraceRecord {
        attribute :>> elementId = "CG-1687BE836F7FC44BCDADF2D2";
        attribute :>> sourceFile = "Rail_MBSE_Function_Interface_v1_final.xlsx";
        attribute :>> sourceSheet = "Connection";
        attribute :>> sourceRow = 20;
    }
    item trace_fae314d9413da718 : TraceRecord {
        attribute :>> elementId = "CG-169E84593A2DDD6DA3BAE4D5";
        attribute :>> sourceFile = "Rail_MBSE_Function_Interface_v1_final.xlsx";
        attribute :>> sourceSheet = "Connection";
        attribute :>> sourceRow = 21;
    }
    item trace_7ed2e6d62787dd90 : TraceRecord {
        attribute :>> elementId = "CG-1803BC1FF5BB8C1A4F69CBA8";
        attribute :>> sourceFile = "Rail_MBSE_Function_Interface_v1_final.xlsx";
        attribute :>> sourceSheet = "Connection";
        attribute :>> sourceRow = 22;
    }
    item trace_c412bd61f1586527 : TraceRecord {
        attribute :>> elementId = "CG-1A5B4FFFE2C9C8ED85759C3D";
        attribute :>> sourceFile = "Rail_MBSE_Function_Interface_v1_final.xlsx";
        attribute :>> sourceSheet = "Connection";
        attribute :>> sourceRow = 23;
    }
    item trace_ef04e8f10aa9caa2 : TraceRecord {
        attribute :>> elementId = "CG-1ACF37CC65D3FF235E8BD75C";
        attribute :>> sourceFile = "Rail_MBSE_Function_Interface_v1_final.xlsx";
        attribute :>> sourceSheet = "Connection";
        attribute :>> sourceRow = 24;
    }
    item trace_ae55a4ec5f3a1204 : TraceRecord {
        attribute :>> elementId = "CG-1AE13610E33C0DC7055CFCED";
        attribute :>> sourceFile = "Rail_MBSE_Function_Interface_v1_final.xlsx";
        attribute :>> sourceSheet = "Connection";
        attribute :>> sourceRow = 25;
    }
    item trace_37124e1eee8c9b32 : TraceRecord {
        attribute :>> elementId = "CG-1AEA8B915E14A5D0FFEE30D9";
        attribute :>> sourceFile = "Rail_MBSE_Function_Interface_v1_final.xlsx";
        attribute :>> sourceSheet = "Connection";
        attribute :>> sourceRow = 26;
    }
    item trace_89925d2ed8a15137 : TraceRecord {
        attribute :>> elementId = "CG-1BA0ACBF380D191A9BED4AE4";
        attribute :>> sourceFile = "Rail_MBSE_Function_Interface_v1_final.xlsx";
        attribute :>> sourceSheet = "Connection";
        attribute :>> sourceRow = 27;
    }
    item trace_8fc972440d46e374 : TraceRecord {
        attribute :>> elementId = "CG-1BF39653E0AA099A8515E223";
        attribute :>> sourceFile = "Rail_MBSE_Function_Interface_v1_final.xlsx";
        attribute :>> sourceSheet = "Connection";
        attribute :>> sourceRow = 28;
    }
    item trace_7a3658f99fa59760 : TraceRecord {
        attribute :>> elementId = "CG-1C5FC46A1E7682144A3BDDDF";
        attribute :>> sourceFile = "Rail_MBSE_Function_Interface_v1_final.xlsx";
        attribute :>> sourceSheet = "Connection";
        attribute :>> sourceRow = 29;
    }
    item trace_0141f16abe4cdd66 : TraceRecord {
        attribute :>> elementId = "CG-1D4D143F52B7F4D880B3CB30";
        attribute :>> sourceFile = "Rail_MBSE_Function_Interface_v1_final.xlsx";
        attribute :>> sourceSheet = "Connection";
        attribute :>> sourceRow = 30;
    }
    item trace_852d4a01054a3a68 : TraceRecord {
        attribute :>> elementId = "CG-1D8165FC25AEFF761DD29797";
        attribute :>> sourceFile = "Rail_MBSE_Function_Interface_v1_final.xlsx";
        attribute :>> sourceSheet = "Connection";
        attribute :>> sourceRow = 31;
    }
    item trace_668a1d5ad757b94e : TraceRecord {
        attribute :>> elementId = "CG-20C0A22ECCF07864FDBA3F5A";
        attribute :>> sourceFile = "Rail_MBSE_Function_Interface_v1_final.xlsx";
        attribute :>> sourceSheet = "Connection";
        attribute :>> sourceRow = 32;
    }
    item trace_4dc879dfb7e7bc53 : TraceRecord {
        attribute :>> elementId = "CG-2274BA128E639FDE4D4F56EC";
        attribute :>> sourceFile = "Rail_MBSE_Function_Interface_v1_final.xlsx";
        attribute :>> sourceSheet = "Connection";
        attribute :>> sourceRow = 33;
    }
    item trace_8a20a7387c541da5 : TraceRecord {
        attribute :>> elementId = "CG-25DC22E45A984D1CB28D188B";
        attribute :>> sourceFile = "Rail_MBSE_Function_Interface_v1_final.xlsx";
        attribute :>> sourceSheet = "Connection";
        attribute :>> sourceRow = 34;
    }
    item trace_ae0b2f4dac2f3825 : TraceRecord {
        attribute :>> elementId = "CG-2B17DCC398F786E916C9C8DC";
        attribute :>> sourceFile = "Rail_MBSE_Function_Interface_v1_final.xlsx";
        attribute :>> sourceSheet = "Connection";
        attribute :>> sourceRow = 35;
    }
    item trace_38dc73184ebf4a19 : TraceRecord {
        attribute :>> elementId = "CG-2C24BA16EF5F2F7E99733CD6";
        attribute :>> sourceFile = "Rail_MBSE_Function_Interface_v1_final.xlsx";
        attribute :>> sourceSheet = "Connection";
        attribute :>> sourceRow = 36;
    }
    item trace_836926ace88f35c7 : TraceRecord {
        attribute :>> elementId = "CG-2C4335E39D698D9A34096F73";
        attribute :>> sourceFile = "Rail_MBSE_Function_Interface_v1_final.xlsx";
        attribute :>> sourceSheet = "Connection";
        attribute :>> sourceRow = 37;
    }
    item trace_eca41cf6d3d6bab7 : TraceRecord {
        attribute :>> elementId = "CG-2CE5C7F366544DF5F5AB234B";
        attribute :>> sourceFile = "Rail_MBSE_Function_Interface_v1_final.xlsx";
        attribute :>> sourceSheet = "Connection";
        attribute :>> sourceRow = 38;
    }
    item trace_f9ea5d4e9c8b8b9d : TraceRecord {
        attribute :>> elementId = "CG-2E8F3CC8A8EBCDE6B7CF4D27";
        attribute :>> sourceFile = "Rail_MBSE_Function_Interface_v1_final.xlsx";
        attribute :>> sourceSheet = "Connection";
        attribute :>> sourceRow = 39;
    }
    item trace_971c6c4ce20bddd3 : TraceRecord {
        attribute :>> elementId = "CG-2EE117B4B0633E38D394B904";
        attribute :>> sourceFile = "Rail_MBSE_Function_Interface_v1_final.xlsx";
        attribute :>> sourceSheet = "Connection";
        attribute :>> sourceRow = 40;
    }
    item trace_448ae5d37b31ce3d : TraceRecord {
        attribute :>> elementId = "CG-3352802713B03806EB2934A1";
        attribute :>> sourceFile = "Rail_MBSE_Function_Interface_v1_final.xlsx";
        attribute :>> sourceSheet = "Connection";
        attribute :>> sourceRow = 41;
    }
    item trace_15a15b1b6dcefa2e : TraceRecord {
        attribute :>> elementId = "CG-338D68ABEF709ACD5E0DDCC6";
        attribute :>> sourceFile = "Rail_MBSE_Function_Interface_v1_final.xlsx";
        attribute :>> sourceSheet = "Connection";
        attribute :>> sourceRow = 42;
    }
    item trace_ff710e09cdd5b3c3 : TraceRecord {
        attribute :>> elementId = "CG-3632726B793CD5429112CAD4";
        attribute :>> sourceFile = "Rail_MBSE_Function_Interface_v1_final.xlsx";
        attribute :>> sourceSheet = "Connection";
        attribute :>> sourceRow = 43;
    }
    item trace_f98cc8b25addb065 : TraceRecord {
        attribute :>> elementId = "CG-37792F42F4274C7C51C63270";
        attribute :>> sourceFile = "Rail_MBSE_Function_Interface_v1_final.xlsx";
        attribute :>> sourceSheet = "Connection";
        attribute :>> sourceRow = 44;
    }
    item trace_df156052f874dec8 : TraceRecord {
        attribute :>> elementId = "CG-37ECA5B04E215AC3E6A4B472";
        attribute :>> sourceFile = "Rail_MBSE_Function_Interface_v1_final.xlsx";
        attribute :>> sourceSheet = "Connection";
        attribute :>> sourceRow = 45;
    }
    item trace_2a7550dbf1d0a18d : TraceRecord {
        attribute :>> elementId = "CG-3981A8B947B66F597AA9E03F";
        attribute :>> sourceFile = "Rail_MBSE_Function_Interface_v1_final.xlsx";
        attribute :>> sourceSheet = "Connection";
        attribute :>> sourceRow = 46;
    }
    item trace_e7ae207c99d8a65a : TraceRecord {
        attribute :>> elementId = "CG-3BD24EBE88F37EEFFE563597";
        attribute :>> sourceFile = "Rail_MBSE_Function_Interface_v1_final.xlsx";
        attribute :>> sourceSheet = "Connection";
        attribute :>> sourceRow = 47;
    }
    item trace_7e5210ce863d5be0 : TraceRecord {
        attribute :>> elementId = "CG-3BE61F5C037C7491E88F4334";
        attribute :>> sourceFile = "Rail_MBSE_Function_Interface_v1_final.xlsx";
        attribute :>> sourceSheet = "Connection";
        attribute :>> sourceRow = 48;
    }
    item trace_1617f3b21f044a83 : TraceRecord {
        attribute :>> elementId = "CG-3CA6C3BF7D7B4F80CF0990D0";
        attribute :>> sourceFile = "Rail_MBSE_Function_Interface_v1_final.xlsx";
        attribute :>> sourceSheet = "Connection";
        attribute :>> sourceRow = 49;
    }
    item trace_2c66f8ce6176dcfd : TraceRecord {
        attribute :>> elementId = "CG-40ADD911FF2840BEEAA67F8D";
        attribute :>> sourceFile = "Rail_MBSE_Function_Interface_v1_final.xlsx";
        attribute :>> sourceSheet = "Connection";
        attribute :>> sourceRow = 50;
    }
    item trace_f4ec3f3f261d53e1 : TraceRecord {
        attribute :>> elementId = "CG-4104726E8B8410405C176AF3";
        attribute :>> sourceFile = "Rail_MBSE_Function_Interface_v1_final.xlsx";
        attribute :>> sourceSheet = "Connection";
        attribute :>> sourceRow = 51;
    }
    item trace_7689437b633a2aa3 : TraceRecord {
        attribute :>> elementId = "CG-410B8D702206200512DD3731";
        attribute :>> sourceFile = "Rail_MBSE_Function_Interface_v1_final.xlsx";
        attribute :>> sourceSheet = "Connection";
        attribute :>> sourceRow = 52;
    }
    item trace_9e640ba934362fd5 : TraceRecord {
        attribute :>> elementId = "CG-4163C3EB1F2D16B7AFCB21C9";
        attribute :>> sourceFile = "Rail_MBSE_Function_Interface_v1_final.xlsx";
        attribute :>> sourceSheet = "Connection";
        attribute :>> sourceRow = 53;
    }
    item trace_205f8e439240c909 : TraceRecord {
        attribute :>> elementId = "CG-41AD09EEB4EAB9DC956C08F8";
        attribute :>> sourceFile = "Rail_MBSE_Function_Interface_v1_final.xlsx";
        attribute :>> sourceSheet = "Connection";
        attribute :>> sourceRow = 54;
    }
    item trace_7ec13f74c1f68599 : TraceRecord {
        attribute :>> elementId = "CG-43EF4A944142319DE5088758";
        attribute :>> sourceFile = "Rail_MBSE_Function_Interface_v1_final.xlsx";
        attribute :>> sourceSheet = "Connection";
        attribute :>> sourceRow = 55;
    }
    item trace_d3072c8cb1fcbf36 : TraceRecord {
        attribute :>> elementId = "CG-44890BAD0E32A867EFFB7EBB";
        attribute :>> sourceFile = "Rail_MBSE_Function_Interface_v1_final.xlsx";
        attribute :>> sourceSheet = "Connection";
        attribute :>> sourceRow = 56;
    }
    item trace_92750bae5e577145 : TraceRecord {
        attribute :>> elementId = "CG-44E8AB4EA7ED953642770E4E";
        attribute :>> sourceFile = "Rail_MBSE_Function_Interface_v1_final.xlsx";
        attribute :>> sourceSheet = "Connection";
        attribute :>> sourceRow = 57;
    }
    item trace_81b3ce5a3bd8ac74 : TraceRecord {
        attribute :>> elementId = "CG-464B2D6F08DDD0D4287D0294";
        attribute :>> sourceFile = "Rail_MBSE_Function_Interface_v1_final.xlsx";
        attribute :>> sourceSheet = "Connection";
        attribute :>> sourceRow = 58;
    }
    item trace_943f93095c65c250 : TraceRecord {
        attribute :>> elementId = "CG-46A1EE350324445D016EAF45";
        attribute :>> sourceFile = "Rail_MBSE_Function_Interface_v1_final.xlsx";
        attribute :>> sourceSheet = "Connection";
        attribute :>> sourceRow = 59;
    }
    item trace_2e6cbfea80b0f38a : TraceRecord {
        attribute :>> elementId = "CG-48B77E7B4DEB11D4F5543CCB";
        attribute :>> sourceFile = "Rail_MBSE_Function_Interface_v1_final.xlsx";
        attribute :>> sourceSheet = "Connection";
        attribute :>> sourceRow = 60;
    }
    item trace_9b4d52ce70dd9b97 : TraceRecord {
        attribute :>> elementId = "CG-4B59832BB120B07245DB82FA";
        attribute :>> sourceFile = "Rail_MBSE_Function_Interface_v1_final.xlsx";
        attribute :>> sourceSheet = "Connection";
        attribute :>> sourceRow = 61;
    }
    item trace_c6c67079d9478ff3 : TraceRecord {
        attribute :>> elementId = "CG-4CB0735167799FD438F90DD2";
        attribute :>> sourceFile = "Rail_MBSE_Function_Interface_v1_final.xlsx";
        attribute :>> sourceSheet = "Connection";
        attribute :>> sourceRow = 62;
    }
    item trace_de711dbef914c3f3 : TraceRecord {
        attribute :>> elementId = "CG-4DBAA813D3DED180F94E9B7F";
        attribute :>> sourceFile = "Rail_MBSE_Function_Interface_v1_final.xlsx";
        attribute :>> sourceSheet = "Connection";
        attribute :>> sourceRow = 63;
    }
    item trace_30cfadd589f08f2c : TraceRecord {
        attribute :>> elementId = "CG-4E4C49F08CEE642A5C3C67EB";
        attribute :>> sourceFile = "Rail_MBSE_Function_Interface_v1_final.xlsx";
        attribute :>> sourceSheet = "Connection";
        attribute :>> sourceRow = 64;
    }
    item trace_5b6687c5f4dc8635 : TraceRecord {
        attribute :>> elementId = "CG-50AB5ECD4830D34487B7B557";
        attribute :>> sourceFile = "Rail_MBSE_Function_Interface_v1_final.xlsx";
        attribute :>> sourceSheet = "Connection";
        attribute :>> sourceRow = 65;
    }
    item trace_23fe5f8a689db9a1 : TraceRecord {
        attribute :>> elementId = "CG-51C22959FEAD177C3827B364";
        attribute :>> sourceFile = "Rail_MBSE_Function_Interface_v1_final.xlsx";
        attribute :>> sourceSheet = "Connection";
        attribute :>> sourceRow = 66;
    }
    item trace_4097ac119708ce90 : TraceRecord {
        attribute :>> elementId = "CG-53ADA5E90929843D3AD53312";
        attribute :>> sourceFile = "Rail_MBSE_Function_Interface_v1_final.xlsx";
        attribute :>> sourceSheet = "Connection";
        attribute :>> sourceRow = 67;
    }
    item trace_7f17a0de60caa3c9 : TraceRecord {
        attribute :>> elementId = "CG-55513667B46680F5B87A0939";
        attribute :>> sourceFile = "Rail_MBSE_Function_Interface_v1_final.xlsx";
        attribute :>> sourceSheet = "Connection";
        attribute :>> sourceRow = 68;
    }
    item trace_41618539e529f37e : TraceRecord {
        attribute :>> elementId = "CG-565AF053FC6E3FF333FD7433";
        attribute :>> sourceFile = "Rail_MBSE_Function_Interface_v1_final.xlsx";
        attribute :>> sourceSheet = "Connection";
        attribute :>> sourceRow = 69;
    }
    item trace_de34283bfce2411a : TraceRecord {
        attribute :>> elementId = "CG-56E4DA6D8C7C1FCFA93A8C7B";
        attribute :>> sourceFile = "Rail_MBSE_Function_Interface_v1_final.xlsx";
        attribute :>> sourceSheet = "Connection";
        attribute :>> sourceRow = 70;
    }
    item trace_9364894b2086d0be : TraceRecord {
        attribute :>> elementId = "CG-57C4C380DFA4E14C0890F4FC";
        attribute :>> sourceFile = "Rail_MBSE_Function_Interface_v1_final.xlsx";
        attribute :>> sourceSheet = "Connection";
        attribute :>> sourceRow = 71;
    }
    item trace_eb02926ab4679d96 : TraceRecord {
        attribute :>> elementId = "CG-585503C9572B9BF371266D8B";
        attribute :>> sourceFile = "Rail_MBSE_Function_Interface_v1_final.xlsx";
        attribute :>> sourceSheet = "Connection";
        attribute :>> sourceRow = 72;
    }
    item trace_20c7ef5584b43cb7 : TraceRecord {
        attribute :>> elementId = "CG-5CC6DABFA52A640C8BC115E5";
        attribute :>> sourceFile = "Rail_MBSE_Function_Interface_v1_final.xlsx";
        attribute :>> sourceSheet = "Connection";
        attribute :>> sourceRow = 73;
    }
    item trace_bcf73f3cd72dcb56 : TraceRecord {
        attribute :>> elementId = "CG-5E309780F220E97DE29B2A38";
        attribute :>> sourceFile = "Rail_MBSE_Function_Interface_v1_final.xlsx";
        attribute :>> sourceSheet = "Connection";
        attribute :>> sourceRow = 74;
    }
    item trace_89f2a988a645b36c : TraceRecord {
        attribute :>> elementId = "CG-61CA88D0219D5B46EEFA0E92";
        attribute :>> sourceFile = "Rail_MBSE_Function_Interface_v1_final.xlsx";
        attribute :>> sourceSheet = "Connection";
        attribute :>> sourceRow = 75;
    }
    item trace_3e39203817e4f68f : TraceRecord {
        attribute :>> elementId = "CG-62B37C74D7B0F1346E00D437";
        attribute :>> sourceFile = "Rail_MBSE_Function_Interface_v1_final.xlsx";
        attribute :>> sourceSheet = "Connection";
        attribute :>> sourceRow = 76;
    }
    item trace_1eb215de2539cf14 : TraceRecord {
        attribute :>> elementId = "CG-6546CFCB7800C785459AC8E1";
        attribute :>> sourceFile = "Rail_MBSE_Function_Interface_v1_final.xlsx";
        attribute :>> sourceSheet = "Connection";
        attribute :>> sourceRow = 77;
    }
    item trace_1f88a5c2dfc752b7 : TraceRecord {
        attribute :>> elementId = "CG-65E377DBF988541FA5778D1E";
        attribute :>> sourceFile = "Rail_MBSE_Function_Interface_v1_final.xlsx";
        attribute :>> sourceSheet = "Connection";
        attribute :>> sourceRow = 78;
    }
    item trace_78c27c56c18e82a4 : TraceRecord {
        attribute :>> elementId = "CG-663CDC611495882DCD3E5B8F";
        attribute :>> sourceFile = "Rail_MBSE_Function_Interface_v1_final.xlsx";
        attribute :>> sourceSheet = "Connection";
        attribute :>> sourceRow = 79;
    }
    item trace_e5d4e2942bcb69b3 : TraceRecord {
        attribute :>> elementId = "CG-676A4A51307B0199D39544B7";
        attribute :>> sourceFile = "Rail_MBSE_Function_Interface_v1_final.xlsx";
        attribute :>> sourceSheet = "Connection";
        attribute :>> sourceRow = 80;
    }
    item trace_a410ab37b0099639 : TraceRecord {
        attribute :>> elementId = "CG-686A357580FCAB93907E7B31";
        attribute :>> sourceFile = "Rail_MBSE_Function_Interface_v1_final.xlsx";
        attribute :>> sourceSheet = "Connection";
        attribute :>> sourceRow = 81;
    }
    item trace_05e9c65e87b5ebd9 : TraceRecord {
        attribute :>> elementId = "CG-686E1C0741D80B3DE2EEBA80";
        attribute :>> sourceFile = "Rail_MBSE_Function_Interface_v1_final.xlsx";
        attribute :>> sourceSheet = "Connection";
        attribute :>> sourceRow = 82;
    }
    item trace_3d92434b60fa04c9 : TraceRecord {
        attribute :>> elementId = "CG-697084EEC1DCA9E975638C14";
        attribute :>> sourceFile = "Rail_MBSE_Function_Interface_v1_final.xlsx";
        attribute :>> sourceSheet = "Connection";
        attribute :>> sourceRow = 83;
    }
    item trace_93266898679ae42b : TraceRecord {
        attribute :>> elementId = "CG-6C6B569AD3F71A70A799D067";
        attribute :>> sourceFile = "Rail_MBSE_Function_Interface_v1_final.xlsx";
        attribute :>> sourceSheet = "Connection";
        attribute :>> sourceRow = 84;
    }
    item trace_b7aee64c67d63643 : TraceRecord {
        attribute :>> elementId = "CG-70D940D7F34BF27762FED746";
        attribute :>> sourceFile = "Rail_MBSE_Function_Interface_v1_final.xlsx";
        attribute :>> sourceSheet = "Connection";
        attribute :>> sourceRow = 85;
    }
    item trace_dfe2c1b7abe7b811 : TraceRecord {
        attribute :>> elementId = "CG-732BB9F5922B7AC9420BB2D0";
        attribute :>> sourceFile = "Rail_MBSE_Function_Interface_v1_final.xlsx";
        attribute :>> sourceSheet = "Connection";
        attribute :>> sourceRow = 86;
    }
    item trace_75a723313f9fa339 : TraceRecord {
        attribute :>> elementId = "CG-734E10C63B7A36C2BB06360D";
        attribute :>> sourceFile = "Rail_MBSE_Function_Interface_v1_final.xlsx";
        attribute :>> sourceSheet = "Connection";
        attribute :>> sourceRow = 87;
    }
    item trace_e28412828d872278 : TraceRecord {
        attribute :>> elementId = "CG-7365C853DD9391D9914E0C8A";
        attribute :>> sourceFile = "Rail_MBSE_Function_Interface_v1_final.xlsx";
        attribute :>> sourceSheet = "Connection";
        attribute :>> sourceRow = 88;
    }
    item trace_2679e096fafa2905 : TraceRecord {
        attribute :>> elementId = "CG-739E53DD845C8CD2646C8E39";
        attribute :>> sourceFile = "Rail_MBSE_Function_Interface_v1_final.xlsx";
        attribute :>> sourceSheet = "Connection";
        attribute :>> sourceRow = 89;
    }
    item trace_57f594398ac6d970 : TraceRecord {
        attribute :>> elementId = "CG-76271B14A422D23C0C6E327D";
        attribute :>> sourceFile = "Rail_MBSE_Function_Interface_v1_final.xlsx";
        attribute :>> sourceSheet = "Connection";
        attribute :>> sourceRow = 90;
    }
    item trace_2e752371a026b085 : TraceRecord {
        attribute :>> elementId = "CG-7664DA49869213FC03120E3B";
        attribute :>> sourceFile = "Rail_MBSE_Function_Interface_v1_final.xlsx";
        attribute :>> sourceSheet = "Connection";
        attribute :>> sourceRow = 91;
    }
    item trace_665214b467bbbce3 : TraceRecord {
        attribute :>> elementId = "CG-767F79CB763B96968C94D7AD";
        attribute :>> sourceFile = "Rail_MBSE_Function_Interface_v1_final.xlsx";
        attribute :>> sourceSheet = "Connection";
        attribute :>> sourceRow = 92;
    }
    item trace_c0ec147379c0b8bf : TraceRecord {
        attribute :>> elementId = "CG-79EB6BEB9B0AE9B2B06844A4";
        attribute :>> sourceFile = "Rail_MBSE_Function_Interface_v1_final.xlsx";
        attribute :>> sourceSheet = "Connection";
        attribute :>> sourceRow = 93;
    }
    item trace_3e8f90e263964183 : TraceRecord {
        attribute :>> elementId = "CG-7A2381DC8C36A40B747035A5";
        attribute :>> sourceFile = "Rail_MBSE_Function_Interface_v1_final.xlsx";
        attribute :>> sourceSheet = "Connection";
        attribute :>> sourceRow = 94;
    }
    item trace_5dea0ac59ba7d34e : TraceRecord {
        attribute :>> elementId = "CG-7AAA105058D4FD893E634E16";
        attribute :>> sourceFile = "Rail_MBSE_Function_Interface_v1_final.xlsx";
        attribute :>> sourceSheet = "Connection";
        attribute :>> sourceRow = 95;
    }
    item trace_9cb5ebb7a8d7f3ca : TraceRecord {
        attribute :>> elementId = "CG-7AEA5BA2801064550BBE6D02";
        attribute :>> sourceFile = "Rail_MBSE_Function_Interface_v1_final.xlsx";
        attribute :>> sourceSheet = "Connection";
        attribute :>> sourceRow = 96;
    }
    item trace_ead7bdf3a0b6a190 : TraceRecord {
        attribute :>> elementId = "CG-7CA35F612B7EF59664CE06F0";
        attribute :>> sourceFile = "Rail_MBSE_Function_Interface_v1_final.xlsx";
        attribute :>> sourceSheet = "Connection";
        attribute :>> sourceRow = 97;
    }
    item trace_6a27b9e7537715c7 : TraceRecord {
        attribute :>> elementId = "CG-7D415C2FE2A98E99E69F2808";
        attribute :>> sourceFile = "Rail_MBSE_Function_Interface_v1_final.xlsx";
        attribute :>> sourceSheet = "Connection";
        attribute :>> sourceRow = 98;
    }
    item trace_8e3b26457e91c871 : TraceRecord {
        attribute :>> elementId = "CG-86987C60BCB826208FEFEF31";
        attribute :>> sourceFile = "Rail_MBSE_Function_Interface_v1_final.xlsx";
        attribute :>> sourceSheet = "Connection";
        attribute :>> sourceRow = 99;
    }
    item trace_b62587c406cbb313 : TraceRecord {
        attribute :>> elementId = "CG-86C48EA2DE057325EEB9853C";
        attribute :>> sourceFile = "Rail_MBSE_Function_Interface_v1_final.xlsx";
        attribute :>> sourceSheet = "Connection";
        attribute :>> sourceRow = 100;
    }
    item trace_cbbb8c60b34c0389 : TraceRecord {
        attribute :>> elementId = "CG-89318B491DF9CED18997C36D";
        attribute :>> sourceFile = "Rail_MBSE_Function_Interface_v1_final.xlsx";
        attribute :>> sourceSheet = "Connection";
        attribute :>> sourceRow = 101;
    }
    item trace_141d80626194d33c : TraceRecord {
        attribute :>> elementId = "CG-89DF67BFD358C3EEF4DB05F2";
        attribute :>> sourceFile = "Rail_MBSE_Function_Interface_v1_final.xlsx";
        attribute :>> sourceSheet = "Connection";
        attribute :>> sourceRow = 102;
    }
    item trace_e8f4ae3a99613ae3 : TraceRecord {
        attribute :>> elementId = "CG-8E2E18108BE2E7B2FB898537";
        attribute :>> sourceFile = "Rail_MBSE_Function_Interface_v1_final.xlsx";
        attribute :>> sourceSheet = "Connection";
        attribute :>> sourceRow = 103;
    }
    item trace_f9fd3ac8a1f45b90 : TraceRecord {
        attribute :>> elementId = "CG-8EE395387745CC0A6FB55207";
        attribute :>> sourceFile = "Rail_MBSE_Function_Interface_v1_final.xlsx";
        attribute :>> sourceSheet = "Connection";
        attribute :>> sourceRow = 104;
    }
    item trace_a5ea3af05f2bd404 : TraceRecord {
        attribute :>> elementId = "CG-8EED0159D22D9EDC70A9EA67";
        attribute :>> sourceFile = "Rail_MBSE_Function_Interface_v1_final.xlsx";
        attribute :>> sourceSheet = "Connection";
        attribute :>> sourceRow = 105;
    }
    item trace_1549e0b95770fbaa : TraceRecord {
        attribute :>> elementId = "CG-8F81398231970DBDB0A7F854";
        attribute :>> sourceFile = "Rail_MBSE_Function_Interface_v1_final.xlsx";
        attribute :>> sourceSheet = "Connection";
        attribute :>> sourceRow = 106;
    }
    item trace_cea2f735396238f3 : TraceRecord {
        attribute :>> elementId = "CG-91B4F6F81C7185E848BAF73E";
        attribute :>> sourceFile = "Rail_MBSE_Function_Interface_v1_final.xlsx";
        attribute :>> sourceSheet = "Connection";
        attribute :>> sourceRow = 107;
    }
    item trace_2b58e056be8643f9 : TraceRecord {
        attribute :>> elementId = "CG-943AD35B9C94E8B079F6212A";
        attribute :>> sourceFile = "Rail_MBSE_Function_Interface_v1_final.xlsx";
        attribute :>> sourceSheet = "Connection";
        attribute :>> sourceRow = 108;
    }
    item trace_d7c6879091b89506 : TraceRecord {
        attribute :>> elementId = "CG-944069F2CBBFA2A01274A9DB";
        attribute :>> sourceFile = "Rail_MBSE_Function_Interface_v1_final.xlsx";
        attribute :>> sourceSheet = "Connection";
        attribute :>> sourceRow = 109;
    }
    item trace_d30f1d70da5d38e7 : TraceRecord {
        attribute :>> elementId = "CG-9465AAC3F0B0B115DC3EF9FD";
        attribute :>> sourceFile = "Rail_MBSE_Function_Interface_v1_final.xlsx";
        attribute :>> sourceSheet = "Connection";
        attribute :>> sourceRow = 110;
    }
    item trace_2070cfad2ce9e48d : TraceRecord {
        attribute :>> elementId = "CG-9731BEC15024660A6C266D47";
        attribute :>> sourceFile = "Rail_MBSE_Function_Interface_v1_final.xlsx";
        attribute :>> sourceSheet = "Connection";
        attribute :>> sourceRow = 111;
    }
    item trace_21812d454d37b6a2 : TraceRecord {
        attribute :>> elementId = "CG-979C19823B520B68E370ECB6";
        attribute :>> sourceFile = "Rail_MBSE_Function_Interface_v1_final.xlsx";
        attribute :>> sourceSheet = "Connection";
        attribute :>> sourceRow = 112;
    }
    item trace_4deb0658aeaee849 : TraceRecord {
        attribute :>> elementId = "CG-992C677E70DA53B7B40EA26C";
        attribute :>> sourceFile = "Rail_MBSE_Function_Interface_v1_final.xlsx";
        attribute :>> sourceSheet = "Connection";
        attribute :>> sourceRow = 113;
    }
    item trace_5e902e91211ddff5 : TraceRecord {
        attribute :>> elementId = "CG-9A05AF4B79F0AC70EEBB8C27";
        attribute :>> sourceFile = "Rail_MBSE_Function_Interface_v1_final.xlsx";
        attribute :>> sourceSheet = "Connection";
        attribute :>> sourceRow = 114;
    }
    item trace_aaf2132425aca407 : TraceRecord {
        attribute :>> elementId = "CG-9ACDE46A41EE650430438B91";
        attribute :>> sourceFile = "Rail_MBSE_Function_Interface_v1_final.xlsx";
        attribute :>> sourceSheet = "Connection";
        attribute :>> sourceRow = 115;
    }
    item trace_228faad53ceb57d1 : TraceRecord {
        attribute :>> elementId = "CG-9AE6E470A1C767E917CAED42";
        attribute :>> sourceFile = "Rail_MBSE_Function_Interface_v1_final.xlsx";
        attribute :>> sourceSheet = "Connection";
        attribute :>> sourceRow = 116;
    }
    item trace_b32a28aea17a6f04 : TraceRecord {
        attribute :>> elementId = "CG-9B0510538F8E21B452D8C165";
        attribute :>> sourceFile = "Rail_MBSE_Function_Interface_v1_final.xlsx";
        attribute :>> sourceSheet = "Connection";
        attribute :>> sourceRow = 117;
    }
    item trace_a692b8e9e49530f4 : TraceRecord {
        attribute :>> elementId = "CG-9D3B4C2BDF604CDEBBA07160";
        attribute :>> sourceFile = "Rail_MBSE_Function_Interface_v1_final.xlsx";
        attribute :>> sourceSheet = "Connection";
        attribute :>> sourceRow = 118;
    }
    item trace_e0b10026c8d8ee3d : TraceRecord {
        attribute :>> elementId = "CG-9EB19436ED0A54ECCF52C717";
        attribute :>> sourceFile = "Rail_MBSE_Function_Interface_v1_final.xlsx";
        attribute :>> sourceSheet = "Connection";
        attribute :>> sourceRow = 119;
    }
    item trace_2ff84085ce561b03 : TraceRecord {
        attribute :>> elementId = "CG-A0B82CF482DDFB4553F8CFCA";
        attribute :>> sourceFile = "Rail_MBSE_Function_Interface_v1_final.xlsx";
        attribute :>> sourceSheet = "Connection";
        attribute :>> sourceRow = 120;
    }
    item trace_25e65c78827e1a89 : TraceRecord {
        attribute :>> elementId = "CG-A0E50849D53632A6F599B298";
        attribute :>> sourceFile = "Rail_MBSE_Function_Interface_v1_final.xlsx";
        attribute :>> sourceSheet = "Connection";
        attribute :>> sourceRow = 121;
    }
    item trace_754e069b1f4100ef : TraceRecord {
        attribute :>> elementId = "CG-A35E2178763C6233BE73AA36";
        attribute :>> sourceFile = "Rail_MBSE_Function_Interface_v1_final.xlsx";
        attribute :>> sourceSheet = "Connection";
        attribute :>> sourceRow = 122;
    }
    item trace_3273e2c7b8169c06 : TraceRecord {
        attribute :>> elementId = "CG-A3B31951ADAE62C498E76260";
        attribute :>> sourceFile = "Rail_MBSE_Function_Interface_v1_final.xlsx";
        attribute :>> sourceSheet = "Connection";
        attribute :>> sourceRow = 123;
    }
    item trace_615a9c498e42e45a : TraceRecord {
        attribute :>> elementId = "CG-A424455519797490E4F865AA";
        attribute :>> sourceFile = "Rail_MBSE_Function_Interface_v1_final.xlsx";
        attribute :>> sourceSheet = "Connection";
        attribute :>> sourceRow = 124;
    }
    item trace_8be8c88ca35cdab9 : TraceRecord {
        attribute :>> elementId = "CG-A467E486FE1FCC1FD2410729";
        attribute :>> sourceFile = "Rail_MBSE_Function_Interface_v1_final.xlsx";
        attribute :>> sourceSheet = "Connection";
        attribute :>> sourceRow = 125;
    }
    item trace_6515360417c3ff61 : TraceRecord {
        attribute :>> elementId = "CG-A6D783BBFCF6C6DA11FFCF2D";
        attribute :>> sourceFile = "Rail_MBSE_Function_Interface_v1_final.xlsx";
        attribute :>> sourceSheet = "Connection";
        attribute :>> sourceRow = 126;
    }
    item trace_ebaf8d2dd7558717 : TraceRecord {
        attribute :>> elementId = "CG-A7173AC81E21DD801A82E73D";
        attribute :>> sourceFile = "Rail_MBSE_Function_Interface_v1_final.xlsx";
        attribute :>> sourceSheet = "Connection";
        attribute :>> sourceRow = 127;
    }
    item trace_a7b05240736dafdd : TraceRecord {
        attribute :>> elementId = "CG-A9A3297C8A71DEFC8975FC31";
        attribute :>> sourceFile = "Rail_MBSE_Function_Interface_v1_final.xlsx";
        attribute :>> sourceSheet = "Connection";
        attribute :>> sourceRow = 128;
    }
    item trace_70a47881f18bb5ff : TraceRecord {
        attribute :>> elementId = "CG-ACA2BC6B6BBEF201778733FC";
        attribute :>> sourceFile = "Rail_MBSE_Function_Interface_v1_final.xlsx";
        attribute :>> sourceSheet = "Connection";
        attribute :>> sourceRow = 129;
    }
    item trace_bd0f3f03e0e9c481 : TraceRecord {
        attribute :>> elementId = "CG-AF75A5003A9B1A8DE28924E1";
        attribute :>> sourceFile = "Rail_MBSE_Function_Interface_v1_final.xlsx";
        attribute :>> sourceSheet = "Connection";
        attribute :>> sourceRow = 130;
    }
    item trace_d50fb1d0ee226165 : TraceRecord {
        attribute :>> elementId = "CG-B1E191297C1D862473B2D371";
        attribute :>> sourceFile = "Rail_MBSE_Function_Interface_v1_final.xlsx";
        attribute :>> sourceSheet = "Connection";
        attribute :>> sourceRow = 131;
    }
    item trace_3dda7ab2be85da91 : TraceRecord {
        attribute :>> elementId = "CG-B251741505CB19FE47559F29";
        attribute :>> sourceFile = "Rail_MBSE_Function_Interface_v1_final.xlsx";
        attribute :>> sourceSheet = "Connection";
        attribute :>> sourceRow = 132;
    }
    item trace_1c723f66ba4b5d81 : TraceRecord {
        attribute :>> elementId = "CG-B399D92EE15558C08A95FA03";
        attribute :>> sourceFile = "Rail_MBSE_Function_Interface_v1_final.xlsx";
        attribute :>> sourceSheet = "Connection";
        attribute :>> sourceRow = 133;
    }
    item trace_cce7396d107cade9 : TraceRecord {
        attribute :>> elementId = "CG-B483D5C4E4EC5F805E3B0F19";
        attribute :>> sourceFile = "Rail_MBSE_Function_Interface_v1_final.xlsx";
        attribute :>> sourceSheet = "Connection";
        attribute :>> sourceRow = 134;
    }
    item trace_ffc9dfba2e1b639c : TraceRecord {
        attribute :>> elementId = "CG-B5CE3B88204C1D03AD0527D2";
        attribute :>> sourceFile = "Rail_MBSE_Function_Interface_v1_final.xlsx";
        attribute :>> sourceSheet = "Connection";
        attribute :>> sourceRow = 135;
    }
    item trace_8741860e036dfc2d : TraceRecord {
        attribute :>> elementId = "CG-B99AB8690BDE418D1F8055E3";
        attribute :>> sourceFile = "Rail_MBSE_Function_Interface_v1_final.xlsx";
        attribute :>> sourceSheet = "Connection";
        attribute :>> sourceRow = 136;
    }
    item trace_722038a47cddf73b : TraceRecord {
        attribute :>> elementId = "CG-BB962E06FB56D8459F9A2BF0";
        attribute :>> sourceFile = "Rail_MBSE_Function_Interface_v1_final.xlsx";
        attribute :>> sourceSheet = "Connection";
        attribute :>> sourceRow = 137;
    }
    item trace_f151b8a785449439 : TraceRecord {
        attribute :>> elementId = "CG-BC53696D702792E563E6C045";
        attribute :>> sourceFile = "Rail_MBSE_Function_Interface_v1_final.xlsx";
        attribute :>> sourceSheet = "Connection";
        attribute :>> sourceRow = 138;
    }
    item trace_88a44754c50b57d2 : TraceRecord {
        attribute :>> elementId = "CG-BDBC6DE36D711BE7257BA6A4";
        attribute :>> sourceFile = "Rail_MBSE_Function_Interface_v1_final.xlsx";
        attribute :>> sourceSheet = "Connection";
        attribute :>> sourceRow = 139;
    }
    item trace_14898f2547f89ee5 : TraceRecord {
        attribute :>> elementId = "CG-BDD8747118488C9BE895D95F";
        attribute :>> sourceFile = "Rail_MBSE_Function_Interface_v1_final.xlsx";
        attribute :>> sourceSheet = "Connection";
        attribute :>> sourceRow = 140;
    }
    item trace_71a7106bd57706fa : TraceRecord {
        attribute :>> elementId = "CG-BDE1416487389FCF7B495D3E";
        attribute :>> sourceFile = "Rail_MBSE_Function_Interface_v1_final.xlsx";
        attribute :>> sourceSheet = "Connection";
        attribute :>> sourceRow = 141;
    }
    item trace_2e8e3d3422efa7cb : TraceRecord {
        attribute :>> elementId = "CG-BE9EAF0E7F50C277DA344138";
        attribute :>> sourceFile = "Rail_MBSE_Function_Interface_v1_final.xlsx";
        attribute :>> sourceSheet = "Connection";
        attribute :>> sourceRow = 142;
    }
    item trace_0d3c9cf8f65e53a1 : TraceRecord {
        attribute :>> elementId = "CG-BEDE0932E86628B2EFCA8CCD";
        attribute :>> sourceFile = "Rail_MBSE_Function_Interface_v1_final.xlsx";
        attribute :>> sourceSheet = "Connection";
        attribute :>> sourceRow = 143;
    }
    item trace_4a86f38e0205aa55 : TraceRecord {
        attribute :>> elementId = "CG-BF14D9A0947A4893C7260661";
        attribute :>> sourceFile = "Rail_MBSE_Function_Interface_v1_final.xlsx";
        attribute :>> sourceSheet = "Connection";
        attribute :>> sourceRow = 144;
    }
    item trace_be4bdc8734b4d515 : TraceRecord {
        attribute :>> elementId = "CG-C003C81FB79009EC9E0DAC6B";
        attribute :>> sourceFile = "Rail_MBSE_Function_Interface_v1_final.xlsx";
        attribute :>> sourceSheet = "Connection";
        attribute :>> sourceRow = 145;
    }
    item trace_9413c35000604066 : TraceRecord {
        attribute :>> elementId = "CG-C03EBDD9B3CFF4E6611E41A1";
        attribute :>> sourceFile = "Rail_MBSE_Function_Interface_v1_final.xlsx";
        attribute :>> sourceSheet = "Connection";
        attribute :>> sourceRow = 146;
    }
    item trace_ca53fe4ea02e72c0 : TraceRecord {
        attribute :>> elementId = "CG-C0F5EB5317440FA36F0491AE";
        attribute :>> sourceFile = "Rail_MBSE_Function_Interface_v1_final.xlsx";
        attribute :>> sourceSheet = "Connection";
        attribute :>> sourceRow = 147;
    }
    item trace_ed8dc7e9a2aa81da : TraceRecord {
        attribute :>> elementId = "CG-C113ED5B462ACDD4ACE56E91";
        attribute :>> sourceFile = "Rail_MBSE_Function_Interface_v1_final.xlsx";
        attribute :>> sourceSheet = "Connection";
        attribute :>> sourceRow = 148;
    }
    item trace_7891fb8cf03fd30a : TraceRecord {
        attribute :>> elementId = "CG-C2F8D7B23A3941D29EE9543F";
        attribute :>> sourceFile = "Rail_MBSE_Function_Interface_v1_final.xlsx";
        attribute :>> sourceSheet = "Connection";
        attribute :>> sourceRow = 149;
    }
    item trace_adddf95eb200eb7e : TraceRecord {
        attribute :>> elementId = "CG-C346B9ABBAE556A332DA422F";
        attribute :>> sourceFile = "Rail_MBSE_Function_Interface_v1_final.xlsx";
        attribute :>> sourceSheet = "Connection";
        attribute :>> sourceRow = 150;
    }
    item trace_193957862c67951a : TraceRecord {
        attribute :>> elementId = "CG-C3FD4BDC3D0E9ABF609DAE81";
        attribute :>> sourceFile = "Rail_MBSE_Function_Interface_v1_final.xlsx";
        attribute :>> sourceSheet = "Connection";
        attribute :>> sourceRow = 151;
    }
    item trace_4927ed1c1bff6d76 : TraceRecord {
        attribute :>> elementId = "CG-C53D41B4A1F64D70B4607AA4";
        attribute :>> sourceFile = "Rail_MBSE_Function_Interface_v1_final.xlsx";
        attribute :>> sourceSheet = "Connection";
        attribute :>> sourceRow = 152;
    }
    item trace_d920f795593a6dfb : TraceRecord {
        attribute :>> elementId = "CG-C5E43804F4CA212D668FD997";
        attribute :>> sourceFile = "Rail_MBSE_Function_Interface_v1_final.xlsx";
        attribute :>> sourceSheet = "Connection";
        attribute :>> sourceRow = 153;
    }
    item trace_a04d30cd4b935579 : TraceRecord {
        attribute :>> elementId = "CG-C64E0682EDDBDDD748BA13CA";
        attribute :>> sourceFile = "Rail_MBSE_Function_Interface_v1_final.xlsx";
        attribute :>> sourceSheet = "Connection";
        attribute :>> sourceRow = 154;
    }
    item trace_76cf48b0e2b799ed : TraceRecord {
        attribute :>> elementId = "CG-C6A9FBA7CCD28311320F3552";
        attribute :>> sourceFile = "Rail_MBSE_Function_Interface_v1_final.xlsx";
        attribute :>> sourceSheet = "Connection";
        attribute :>> sourceRow = 155;
    }
    item trace_f0da4bef0c509ab0 : TraceRecord {
        attribute :>> elementId = "CG-C7C6703197747322B57096B5";
        attribute :>> sourceFile = "Rail_MBSE_Function_Interface_v1_final.xlsx";
        attribute :>> sourceSheet = "Connection";
        attribute :>> sourceRow = 156;
    }
    item trace_5526b27ce69253fc : TraceRecord {
        attribute :>> elementId = "CG-C81A2253CDA9FC6173740074";
        attribute :>> sourceFile = "Rail_MBSE_Function_Interface_v1_final.xlsx";
        attribute :>> sourceSheet = "Connection";
        attribute :>> sourceRow = 157;
    }
    item trace_67aa23631804438a : TraceRecord {
        attribute :>> elementId = "CG-C8FE042475056BF85CFA2B40";
        attribute :>> sourceFile = "Rail_MBSE_Function_Interface_v1_final.xlsx";
        attribute :>> sourceSheet = "Connection";
        attribute :>> sourceRow = 158;
    }
    item trace_79f07668e7610fe3 : TraceRecord {
        attribute :>> elementId = "CG-C9CA06B236DB453EEFEC07E6";
        attribute :>> sourceFile = "Rail_MBSE_Function_Interface_v1_final.xlsx";
        attribute :>> sourceSheet = "Connection";
        attribute :>> sourceRow = 159;
    }
    item trace_a02db308ad4002d1 : TraceRecord {
        attribute :>> elementId = "CG-CB302083C9F33A1345D9C406";
        attribute :>> sourceFile = "Rail_MBSE_Function_Interface_v1_final.xlsx";
        attribute :>> sourceSheet = "Connection";
        attribute :>> sourceRow = 160;
    }
    item trace_4579da11685579f5 : TraceRecord {
        attribute :>> elementId = "CG-CCE3D228C7F2AEE6207C1B6A";
        attribute :>> sourceFile = "Rail_MBSE_Function_Interface_v1_final.xlsx";
        attribute :>> sourceSheet = "Connection";
        attribute :>> sourceRow = 161;
    }
    item trace_c02c791c1dc2836f : TraceRecord {
        attribute :>> elementId = "CG-CD05C34D37DBECA08731CAFA";
        attribute :>> sourceFile = "Rail_MBSE_Function_Interface_v1_final.xlsx";
        attribute :>> sourceSheet = "Connection";
        attribute :>> sourceRow = 162;
    }
    item trace_e14850df965046bf : TraceRecord {
        attribute :>> elementId = "CG-CE151D40A2BF816F41762F4C";
        attribute :>> sourceFile = "Rail_MBSE_Function_Interface_v1_final.xlsx";
        attribute :>> sourceSheet = "Connection";
        attribute :>> sourceRow = 163;
    }
    item trace_c35c5444bd213837 : TraceRecord {
        attribute :>> elementId = "CG-CE2820923CC0CB141833E11D";
        attribute :>> sourceFile = "Rail_MBSE_Function_Interface_v1_final.xlsx";
        attribute :>> sourceSheet = "Connection";
        attribute :>> sourceRow = 164;
    }
    item trace_20753aaf53e80b69 : TraceRecord {
        attribute :>> elementId = "CG-D1D66AE9099CD7FA32C270A6";
        attribute :>> sourceFile = "Rail_MBSE_Function_Interface_v1_final.xlsx";
        attribute :>> sourceSheet = "Connection";
        attribute :>> sourceRow = 165;
    }
    item trace_f3b197793880b65d : TraceRecord {
        attribute :>> elementId = "CG-D2E26B7066F1A62115B06D59";
        attribute :>> sourceFile = "Rail_MBSE_Function_Interface_v1_final.xlsx";
        attribute :>> sourceSheet = "Connection";
        attribute :>> sourceRow = 166;
    }
    item trace_ccb033033a14d868 : TraceRecord {
        attribute :>> elementId = "CG-D338FAEF97B977B2FE95051B";
        attribute :>> sourceFile = "Rail_MBSE_Function_Interface_v1_final.xlsx";
        attribute :>> sourceSheet = "Connection";
        attribute :>> sourceRow = 167;
    }
    item trace_d9081cd165414553 : TraceRecord {
        attribute :>> elementId = "CG-D44FA955851A05FB81FD0837";
        attribute :>> sourceFile = "Rail_MBSE_Function_Interface_v1_final.xlsx";
        attribute :>> sourceSheet = "Connection";
        attribute :>> sourceRow = 168;
    }
    item trace_5b01ad45f29b03d7 : TraceRecord {
        attribute :>> elementId = "CG-D4DF5719633CB5B375F35094";
        attribute :>> sourceFile = "Rail_MBSE_Function_Interface_v1_final.xlsx";
        attribute :>> sourceSheet = "Connection";
        attribute :>> sourceRow = 169;
    }
    item trace_b4bf67697ebce69e : TraceRecord {
        attribute :>> elementId = "CG-D8FCE908D4FD9343C6353985";
        attribute :>> sourceFile = "Rail_MBSE_Function_Interface_v1_final.xlsx";
        attribute :>> sourceSheet = "Connection";
        attribute :>> sourceRow = 170;
    }
    item trace_44bee59a0772504b : TraceRecord {
        attribute :>> elementId = "CG-D9445FD2D7B8285174B3AE22";
        attribute :>> sourceFile = "Rail_MBSE_Function_Interface_v1_final.xlsx";
        attribute :>> sourceSheet = "Connection";
        attribute :>> sourceRow = 171;
    }
    item trace_c1411a6deea14f7a : TraceRecord {
        attribute :>> elementId = "CG-D9940860A6DB9E6BD5200881";
        attribute :>> sourceFile = "Rail_MBSE_Function_Interface_v1_final.xlsx";
        attribute :>> sourceSheet = "Connection";
        attribute :>> sourceRow = 172;
    }
    item trace_df838efe5c864e4b : TraceRecord {
        attribute :>> elementId = "CG-D9CD1E8933F596F319A67625";
        attribute :>> sourceFile = "Rail_MBSE_Function_Interface_v1_final.xlsx";
        attribute :>> sourceSheet = "Connection";
        attribute :>> sourceRow = 173;
    }
    item trace_7ba4fe272f32ebd4 : TraceRecord {
        attribute :>> elementId = "CG-DA869E241F8A36DBAAC07E48";
        attribute :>> sourceFile = "Rail_MBSE_Function_Interface_v1_final.xlsx";
        attribute :>> sourceSheet = "Connection";
        attribute :>> sourceRow = 174;
    }
    item trace_d1d09846fb1c4fca : TraceRecord {
        attribute :>> elementId = "CG-DAF7D43DDD825831F29A70F8";
        attribute :>> sourceFile = "Rail_MBSE_Function_Interface_v1_final.xlsx";
        attribute :>> sourceSheet = "Connection";
        attribute :>> sourceRow = 175;
    }
    item trace_d432440155e7d743 : TraceRecord {
        attribute :>> elementId = "CG-E0DB6C9771E2E272BC041D82";
        attribute :>> sourceFile = "Rail_MBSE_Function_Interface_v1_final.xlsx";
        attribute :>> sourceSheet = "Connection";
        attribute :>> sourceRow = 176;
    }
    item trace_a425c5de6ffe3cac : TraceRecord {
        attribute :>> elementId = "CG-E5A3740D9F06BF31CB55A481";
        attribute :>> sourceFile = "Rail_MBSE_Function_Interface_v1_final.xlsx";
        attribute :>> sourceSheet = "Connection";
        attribute :>> sourceRow = 177;
    }
    item trace_2505392d53191979 : TraceRecord {
        attribute :>> elementId = "CG-E85E42C2A83EE58624438A26";
        attribute :>> sourceFile = "Rail_MBSE_Function_Interface_v1_final.xlsx";
        attribute :>> sourceSheet = "Connection";
        attribute :>> sourceRow = 178;
    }
    item trace_a33aab7223dcf6cc : TraceRecord {
        attribute :>> elementId = "CG-E8DAA56D71F2BE4B5E1C9BBF";
        attribute :>> sourceFile = "Rail_MBSE_Function_Interface_v1_final.xlsx";
        attribute :>> sourceSheet = "Connection";
        attribute :>> sourceRow = 179;
    }
    item trace_58ef167ef7c36b3e : TraceRecord {
        attribute :>> elementId = "CG-E9224B53F74EDFCCFDA0FC70";
        attribute :>> sourceFile = "Rail_MBSE_Function_Interface_v1_final.xlsx";
        attribute :>> sourceSheet = "Connection";
        attribute :>> sourceRow = 180;
    }
    item trace_99a7d475f3d4ec50 : TraceRecord {
        attribute :>> elementId = "CG-E9AAF8010953F56E28D65ACF";
        attribute :>> sourceFile = "Rail_MBSE_Function_Interface_v1_final.xlsx";
        attribute :>> sourceSheet = "Connection";
        attribute :>> sourceRow = 181;
    }
    item trace_45ec3930b87ce307 : TraceRecord {
        attribute :>> elementId = "CG-ED49C68C1459BB1005D412BB";
        attribute :>> sourceFile = "Rail_MBSE_Function_Interface_v1_final.xlsx";
        attribute :>> sourceSheet = "Connection";
        attribute :>> sourceRow = 182;
    }
    item trace_0c37b04833b7c69b : TraceRecord {
        attribute :>> elementId = "CG-F55B5E17D8CBFAC80E0961C2";
        attribute :>> sourceFile = "Rail_MBSE_Function_Interface_v1_final.xlsx";
        attribute :>> sourceSheet = "Connection";
        attribute :>> sourceRow = 183;
    }
    item trace_7a22ddd0f052e560 : TraceRecord {
        attribute :>> elementId = "CG-F69B9F4B8E034908EE3FE467";
        attribute :>> sourceFile = "Rail_MBSE_Function_Interface_v1_final.xlsx";
        attribute :>> sourceSheet = "Connection";
        attribute :>> sourceRow = 184;
    }
    item trace_5aaf679ec85dcb7e : TraceRecord {
        attribute :>> elementId = "CG-F85BCC7C68AD281053865693";
        attribute :>> sourceFile = "Rail_MBSE_Function_Interface_v1_final.xlsx";
        attribute :>> sourceSheet = "Connection";
        attribute :>> sourceRow = 185;
    }
    item trace_89acb94ae3eac17a : TraceRecord {
        attribute :>> elementId = "CG-FA31DFA220FEF0D6FAC8EB67";
        attribute :>> sourceFile = "Rail_MBSE_Function_Interface_v1_final.xlsx";
        attribute :>> sourceSheet = "Connection";
        attribute :>> sourceRow = 186;
    }
    item trace_7b3a5f75d05aa775 : TraceRecord {
        attribute :>> elementId = "CG-FD763799DECBFD4A6F4F94AD";
        attribute :>> sourceFile = "Rail_MBSE_Function_Interface_v1_final.xlsx";
        attribute :>> sourceSheet = "Connection";
        attribute :>> sourceRow = 187;
    }
    item trace_9b0d82d4b576926a : TraceRecord {
        attribute :>> elementId = "CG-FE573ED935CFF37491A053E8";
        attribute :>> sourceFile = "Rail_MBSE_Function_Interface_v1_final.xlsx";
        attribute :>> sourceSheet = "Connection";
        attribute :>> sourceRow = 188;
    }
    item trace_877fddf833071ef9 : TraceRecord {
        attribute :>> elementId = "NET-DC-LINK-01";
        attribute :>> sourceFile = "Rail_MBSE_Function_Interface_v1_final.xlsx";
        attribute :>> sourceSheet = "PhysicalNet";
        attribute :>> sourceRow = 5;
    }
    item trace_0488d582260e7594 : TraceRecord {
        attribute :>> elementId = "NET-LVDC-CONTROL-01";
        attribute :>> sourceFile = "Rail_MBSE_Function_Interface_v1_final.xlsx";
        attribute :>> sourceSheet = "PhysicalNet";
        attribute :>> sourceRow = 6;
    }
    item trace_b9763ba3314e3a1a : TraceRecord {
        attribute :>> elementId = "NET-MAIN-RETURN-01";
        attribute :>> sourceFile = "Rail_MBSE_Function_Interface_v1_final.xlsx";
        attribute :>> sourceSheet = "PhysicalNet";
        attribute :>> sourceRow = 7;
    }
    item trace_3bcee1c6b279faf2 : TraceRecord {
        attribute :>> elementId = "NET-PNEU-BRAKE-SUPPLY-01";
        attribute :>> sourceFile = "Rail_MBSE_Function_Interface_v1_final.xlsx";
        attribute :>> sourceSheet = "PhysicalNet";
        attribute :>> sourceRow = 8;
    }
    item trace_44b65f0e8d1d0683 : TraceRecord {
        attribute :>> elementId = "NET-PNEU-CYLINDER-01";
        attribute :>> sourceFile = "Rail_MBSE_Function_Interface_v1_final.xlsx";
        attribute :>> sourceSheet = "PhysicalNet";
        attribute :>> sourceRow = 9;
    }
    item trace_6d492814993382d9 : TraceRecord {
        attribute :>> elementId = "NET-PNEU-MAIN-01";
        attribute :>> sourceFile = "Rail_MBSE_Function_Interface_v1_final.xlsx";
        attribute :>> sourceSheet = "PhysicalNet";
        attribute :>> sourceRow = 10;
    }
    item trace_20eaeba1b9ead71e : TraceRecord {
        attribute :>> elementId = "NET-STORAGE-DC-AFTER-CONTACTOR-01";
        attribute :>> sourceFile = "Rail_MBSE_Function_Interface_v1_final.xlsx";
        attribute :>> sourceSheet = "PhysicalNet";
        attribute :>> sourceRow = 11;
    }
    item trace_08529812c89b1dd1 : TraceRecord {
        attribute :>> elementId = "NET-STORAGE-DC-BUS-01";
        attribute :>> sourceFile = "Rail_MBSE_Function_Interface_v1_final.xlsx";
        attribute :>> sourceSheet = "PhysicalNet";
        attribute :>> sourceRow = 12;
    }
    item trace_cec2fda7632db005 : TraceRecord {
        attribute :>> elementId = "NET-STORAGE-DC-SC-01";
        attribute :>> sourceFile = "Rail_MBSE_Function_Interface_v1_final.xlsx";
        attribute :>> sourceSheet = "PhysicalNet";
        attribute :>> sourceRow = 13;
    }
}

package Rail_MBSE {
    private import GeneralDefinitions::*;
    private import SystemDefinition::*;
    private import FunctionAllocations::*;
    private import PhysicalNetworks::*;
    private import Traceability::*;
}
