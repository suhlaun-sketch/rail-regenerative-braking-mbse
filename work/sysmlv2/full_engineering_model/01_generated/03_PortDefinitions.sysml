package PortDefinitions {
    private import ItemDefinitions::*;
    port def PT_PT_ACC_001 {
        out item payload : I_ITM_ACC_001;
    }
    port def PT_PT_ACC_002 {
        out item payload : I_ITM_ACC_002;
    }
    port def PT_PT_ACC_003 {
        out item payload : I_ITM_ACC_003;
    }
    port def PT_PT_ACC_004 {
        out item payload : I_ITM_ACC_004;
    }
    port def PT_PT_ACC_005 {
        out item payload : I_ITM_ACC_005;
    }
    port def PT_PT_ACC_006 {
        out item payload : I_ITM_ACC_006;
    }
    port def PT_PT_ACC_007 {
        out item payload : I_ITM_ACC_007;
    }
    port def PT_PT_ACC_008 {
        out item payload : I_ITM_ACC_008;
    }
    port def PT_PT_ACC_009 {
        out item payload : I_ITM_ACC_009;
    }
    port def PT_PT_ACC_010 {
        out item payload : I_ITM_ACC_010;
    }
    port def PT_PT_ACC_011 {
        out item payload : I_ITM_ACC_011;
    }
    port def PT_PT_ACC_012 {
        out item payload : I_ITM_ACC_012;
    }
    port def PT_PT_ACC_013 {
        out item payload : I_ITM_ACC_013;
    }
    port def PT_PT_ACC_014 {
        out item payload : I_ITM_ACC_014;
    }
    port def PT_PT_ACC_015 {
        out item payload : I_ITM_ACC_015;
    }
    port def PT_PT_CMD_001 {
        out item payload : I_ITM_CMD_001;
    }
    port def PT_PT_CMD_002 {
        out item payload : I_ITM_CMD_002;
    }
    port def PT_PT_CMD_003 {
        out item payload : I_ITM_CMD_003;
    }
    port def PT_PT_CMD_004 {
        out item payload : I_ITM_CMD_004;
    }
    port def PT_PT_CMD_005 {
        out item payload : I_ITM_CMD_005;
    }
    port def PT_PT_CMD_006 {
        out item payload : I_ITM_CMD_006;
    }
    port def PT_PT_CMD_007 {
        out item payload : I_ITM_CMD_007;
    }
    port def PT_PT_CMD_008 {
        out item payload : I_ITM_CMD_008;
    }
    port def PT_PT_CMD_009 {
        out item payload : I_ITM_CMD_009;
    }
    port def PT_PT_CMD_010 {
        out item payload : I_ITM_CMD_010;
    }
    port def PT_PT_CMD_011 {
        out item payload : I_ITM_CMD_011;
    }
    port def PT_PT_CMD_012 {
        out item payload : I_ITM_CMD_012;
    }
    port def PT_PT_CMD_013 {
        out item payload : I_ITM_CMD_013;
    }
    port def PT_PT_CMD_014 {
        out item payload : I_ITM_CMD_014;
    }
    port def PT_PT_CMD_015 {
        out item payload : I_ITM_CMD_015;
    }
    port def PT_PT_CMD_016 {
        out item payload : I_ITM_CMD_016;
    }
    port def PT_PT_CMD_017 {
        out item payload : I_ITM_CMD_017;
    }
    port def PT_PT_CMD_018 {
        out item payload : I_ITM_CMD_018;
    }
    port def PT_PT_CMD_019 {
        out item payload : I_ITM_CMD_019;
    }
    port def PT_PT_CMD_020 {
        out item payload : I_ITM_CMD_020;
    }
    port def PT_PT_CMD_021 {
        out item payload : I_ITM_CMD_021;
    }
    port def PT_PT_CMD_022 {
        out item payload : I_ITM_CMD_022;
    }
    port def PT_PT_CMD_023 {
        out item payload : I_ITM_CMD_023;
    }
    port def PT_PT_CMD_024 {
        out item payload : I_ITM_CMD_024;
    }
    port def PT_PT_CMD_025 {
        out item payload : I_ITM_CMD_025;
    }
    port def PT_PT_CMD_026 {
        out item payload : I_ITM_CMD_026;
    }
    port def PT_PT_CMD_027 {
        out item payload : I_ITM_CMD_027;
    }
    port def PT_PT_CMD_028 {
        out item payload : I_ITM_CMD_028;
    }
    port def PT_PT_CMD_029 {
        out item payload : I_ITM_CMD_029;
    }
    port def PT_PT_CMD_030 {
        out item payload : I_ITM_CMD_030;
    }
    port def PT_PT_CMD_031 {
        out item payload : I_ITM_CMD_031;
    }
    port def PT_PT_CMD_032 {
        out item payload : I_ITM_CMD_032;
    }
    port def PT_PT_LIM_001 {
        out item payload : I_ITM_LIM_001;
    }
    port def PT_PT_LIM_002 {
        out item payload : I_ITM_LIM_002;
    }
    port def PT_PT_LIM_003 {
        out item payload : I_ITM_LIM_003;
    }
    port def PT_PT_LIM_004 {
        out item payload : I_ITM_LIM_004;
    }
    port def PT_PT_LIM_005 {
        out item payload : I_ITM_LIM_005;
    }
    port def PT_PT_LIM_006 {
        out item payload : I_ITM_LIM_006;
    }
    port def PT_PT_LIM_007 {
        out item payload : I_ITM_LIM_007;
    }
    port def PT_PT_LIM_008 {
        out item payload : I_ITM_LIM_008;
    }
    port def PT_PT_LIM_009 {
        out item payload : I_ITM_LIM_009;
    }
    port def PT_PT_LIM_010 {
        out item payload : I_ITM_LIM_010;
    }
    port def PT_PT_LIM_011 {
        out item payload : I_ITM_LIM_011;
    }
    port def PT_PT_LIM_012 {
        out item payload : I_ITM_LIM_012;
    }
    port def PT_PT_LIM_013 {
        out item payload : I_ITM_LIM_013;
    }
    port def PT_PT_LIM_014 {
        out item payload : I_ITM_LIM_014;
    }
    port def PT_PT_MEA_001 {
        out item payload : I_ITM_MEA_001;
    }
    port def PT_PT_MEA_002 {
        out item payload : I_ITM_MEA_002;
    }
    port def PT_PT_MEA_003 {
        out item payload : I_ITM_MEA_003;
    }
    port def PT_PT_MEA_004 {
        out item payload : I_ITM_MEA_004;
    }
    port def PT_PT_MEA_005 {
        out item payload : I_ITM_MEA_005;
    }
    port def PT_PT_MEA_006 {
        out item payload : I_ITM_MEA_006;
    }
    port def PT_PT_MEA_007 {
        out item payload : I_ITM_MEA_007;
    }
    port def PT_PT_MEA_008 {
        out item payload : I_ITM_MEA_008;
    }
    port def PT_PT_MEA_009 {
        out item payload : I_ITM_MEA_009;
    }
    port def PT_PT_MEA_010 {
        out item payload : I_ITM_MEA_010;
    }
    port def PT_PT_MEA_011 {
        out item payload : I_ITM_MEA_011;
    }
    port def PT_PT_MEA_012 {
        out item payload : I_ITM_MEA_012;
    }
    port def PT_PT_MEA_013 {
        out item payload : I_ITM_MEA_013;
    }
    port def PT_PT_MEA_014 {
        out item payload : I_ITM_MEA_014;
    }
    port def PT_PT_MEA_015 {
        out item payload : I_ITM_MEA_015;
    }
    port def PT_PT_MEA_016 {
        out item payload : I_ITM_MEA_016;
    }
    port def PT_PT_MEA_017 {
        out item payload : I_ITM_MEA_017;
    }
    port def PT_PT_MEA_018 {
        out item payload : I_ITM_MEA_018;
    }
    port def PT_PT_MEA_019 {
        out item payload : I_ITM_MEA_019;
    }
    port def PT_PT_MEA_020 {
        out item payload : I_ITM_MEA_020;
    }
    port def PT_PT_MEA_021 {
        out item payload : I_ITM_MEA_021;
    }
    port def PT_PT_MEA_022 {
        out item payload : I_ITM_MEA_022;
    }
    port def PT_PT_MEA_023 {
        out item payload : I_ITM_MEA_023;
    }
    port def PT_PT_MEA_024 {
        out item payload : I_ITM_MEA_024;
    }
    port def PT_PT_MEA_025 {
        out item payload : I_ITM_MEA_025;
    }
    port def PT_PT_MEA_026 {
        out item payload : I_ITM_MEA_026;
    }
    port def PT_PT_MEA_027 {
        out item payload : I_ITM_MEA_027;
    }
    port def PT_PT_MEA_028 {
        out item payload : I_ITM_MEA_028;
    }
    port def PT_PT_MEA_029 {
        out item payload : I_ITM_MEA_029;
    }
    port def PT_PT_MEA_030 {
        out item payload : I_ITM_MEA_030;
    }
    port def PT_PT_MEA_031 {
        out item payload : I_ITM_MEA_031;
    }
    port def PT_PT_PHY_001 {
        inout item payload : I_ITM_PHY_001;
    }
    port def PT_PT_PHY_002 {
        inout item payload : I_ITM_PHY_002;
    }
    port def PT_PT_PHY_003 {
        inout item payload : I_ITM_PHY_003;
    }
    port def PT_PT_PHY_004 {
        inout item payload : I_ITM_PHY_004;
    }
    port def PT_PT_PHY_005 {
        inout item payload : I_ITM_PHY_005;
    }
    port def PT_PT_PHY_006 {
        inout item payload : I_ITM_PHY_006;
    }
    port def PT_PT_PHY_007 {
        inout item payload : I_ITM_PHY_007;
    }
    port def PT_PT_PHY_008 {
        inout item payload : I_ITM_PHY_008;
    }
    port def PT_PT_PHY_009 {
        inout item payload : I_ITM_PHY_009;
    }
    port def PT_PT_PHY_010 {
        inout item payload : I_ITM_PHY_010;
    }
    port def PT_PT_PHY_011 {
        inout item payload : I_ITM_PHY_011;
    }
    port def PT_PT_PHY_012 {
        inout item payload : I_ITM_PHY_012;
    }
    port def PT_PT_PHY_013 {
        inout item payload : I_ITM_PHY_013;
    }
    port def PT_PT_PHY_014 {
        inout item payload : I_ITM_PHY_014;
    }
    port def PT_PT_PHY_015 {
        inout item payload : I_ITM_PHY_015;
    }
    port def PT_PT_PHY_016 {
        inout item payload : I_ITM_PHY_016;
    }
    port def PT_PT_STA_001 {
        out item payload : I_ITM_STA_001;
    }
    port def PT_PT_STA_002 {
        out item payload : I_ITM_STA_002;
    }
    port def PT_PT_STA_003 {
        out item payload : I_ITM_STA_003;
    }
    port def PT_PT_STA_004 {
        out item payload : I_ITM_STA_004;
    }
    port def PT_PT_STA_005 {
        out item payload : I_ITM_STA_005;
    }
    port def PT_PT_STA_006 {
        out item payload : I_ITM_STA_006;
    }
    port def PT_PT_STA_007 {
        out item payload : I_ITM_STA_007;
    }
    port def PT_PT_STA_008 {
        out item payload : I_ITM_STA_008;
    }
    port def PT_PT_STA_009 {
        out item payload : I_ITM_STA_009;
    }
    port def PT_PT_STA_010 {
        out item payload : I_ITM_STA_010;
    }
    port def PT_PT_STA_011 {
        out item payload : I_ITM_STA_011;
    }
    port def PT_PT_STA_012 {
        out item payload : I_ITM_STA_012;
    }
    port def PT_PT_STA_013 {
        out item payload : I_ITM_STA_013;
    }
    port def PT_PT_STA_014 {
        out item payload : I_ITM_STA_014;
    }
    port def PT_PT_STA_015 {
        out item payload : I_ITM_STA_015;
    }
    port def PT_PT_STA_016 {
        out item payload : I_ITM_STA_016;
    }
    port def PT_PT_STA_017 {
        out item payload : I_ITM_STA_017;
    }
    port def PT_PT_STA_018 {
        out item payload : I_ITM_STA_018;
    }
    port def PT_PT_STA_019 {
        out item payload : I_ITM_STA_019;
    }
    port def PT_PT_STA_020 {
        out item payload : I_ITM_STA_020;
    }
    port def PT_PT_STA_021 {
        out item payload : I_ITM_STA_021;
    }
    port def PT_PT_STA_022 {
        out item payload : I_ITM_STA_022;
    }
    port def PT_PT_STA_023 {
        out item payload : I_ITM_STA_023;
    }
    port def PT_PT_STA_024 {
        out item payload : I_ITM_STA_024;
    }
    port def PT_PT_STA_025 {
        out item payload : I_ITM_STA_025;
    }
    port def PT_PT_STA_026 {
        out item payload : I_ITM_STA_026;
    }
    port def PT_PT_STA_027 {
        out item payload : I_ITM_STA_027;
    }
    port def PT_PT_STA_028 {
        out item payload : I_ITM_STA_028;
    }
    port def PT_PT_STA_029 {
        out item payload : I_ITM_STA_029;
    }
    port def PT_PT_STA_030 {
        out item payload : I_ITM_STA_030;
    }
    port def PT_PT_STA_031 {
        out item payload : I_ITM_STA_031;
    }
    port def PT_PT_STA_032 {
        out item payload : I_ITM_STA_032;
    }
    port def PT_PT_STA_033 {
        out item payload : I_ITM_STA_033;
    }
    port def PT_PT_STA_034 {
        out item payload : I_ITM_STA_034;
    }
    port def PT_PT_STA_035 {
        out item payload : I_ITM_STA_035;
    }
    port def PT_PT_STA_036 {
        out item payload : I_ITM_STA_036;
    }
}
