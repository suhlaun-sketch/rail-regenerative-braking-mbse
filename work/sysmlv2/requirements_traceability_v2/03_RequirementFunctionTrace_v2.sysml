package RequirementFunctionTraceV2 {
    private import RequirementDefinitionsV2::*;
    private import FunctionAllocations::*;

    // Each satisfy usage is copied directly from the V2 Excel mapping sheet; the by-end references the frozen model's allocated action usage.
    satisfy req_REQ_ENE_001 by fu_F_X100_01;
    satisfy req_PRJ_ENE_001 by fu_F_X100_01;
    satisfy req_PRJ_ENE_004 by fu_F_X100_01;
    satisfy req_REQ_TRAC_001 by fu_F_5132_01;
    satisfy req_REQ_TRAC_001 by fu_F_5311_01;
    satisfy req_REQ_TRAC_001 by fu_F_5311_02;
    satisfy req_REQ_TRAC_001 by fu_F_5112_01;
    satisfy req_REQ_TRAC_002 by fu_F_5132_01;
    satisfy req_REQ_TRAC_002 by fu_F_5311_01;
    satisfy req_REQ_TRAC_002 by fu_F_5311_02;
    satisfy req_REQ_TRAC_002 by fu_F_5112_01;
    satisfy req_REQ_TRAC_003 by fu_F_7211_04;
    satisfy req_REQ_TRAC_003 by fu_F_722A_01;
    satisfy req_REQ_TRAC_003 by fu_F_5311_02;
    satisfy req_REQ_TRAC_004 by fu_F_4511_01;
    satisfy req_REQ_TRAC_004 by fu_F_5131_01;
    satisfy req_REQ_TRAC_004 by fu_F_5132_01;
    satisfy req_REQ_TRAC_004 by fu_F_5311_01;
    satisfy req_REQ_BRK_001 by fu_F_7211_01;
    satisfy req_REQ_BRK_001 by fu_F_7211_02;
    satisfy req_REQ_BRK_001 by fu_F_7211_03;
    satisfy req_REQ_BRK_001 by fu_F_7255_01;
    satisfy req_REQ_BRK_001 by fu_F_5311_01;
    satisfy req_REQ_BRK_002 by fu_F_7211_04;
    satisfy req_REQ_BRK_002 by fu_F_7226_01;
    satisfy req_REQ_BRK_002 by fu_F_7255_01;
    satisfy req_REQ_BRK_002 by fu_F_D121_01;
    satisfy req_REQ_BRK_003 by fu_F_7211_02;
    satisfy req_REQ_BRK_003 by fu_F_7211_03;
    satisfy req_REQ_BRK_003 by fu_F_7255_01;
    satisfy req_REQ_BRK_004 by fu_F_7211_02;
    satisfy req_REQ_BRK_004 by fu_F_7211_03;
    satisfy req_REQ_BRK_004 by fu_F_5311_01;
    satisfy req_REQ_BRK_004 by fu_F_7255_01;
    satisfy req_REQ_BRK_005 by fu_F_7224_01;
    satisfy req_REQ_BRK_005 by fu_F_7211_01;
    satisfy req_REQ_BRK_006 by fu_F_7211_02;
    satisfy req_REQ_BRK_006 by fu_F_5311_01;
    satisfy req_REQ_BRK_006 by fu_F_7255_01;
    satisfy req_REQ_BRK_007 by fu_F_7211_02;
    satisfy req_REQ_BRK_007 by fu_F_5311_01;
    satisfy req_REQ_BRK_007 by fu_F_X121_01;
    satisfy req_REQ_BRK_007 by fu_F_X112_02;
    satisfy req_REQ_BRK_008 by fu_F_7211_02;
    satisfy req_REQ_BRK_008 by fu_F_7211_03;
    satisfy req_REQ_BRK_008 by fu_F_7255_01;
    satisfy req_REQ_BRK_009 by fu_F_7211_02;
    satisfy req_REQ_BRK_009 by fu_F_7211_03;
    satisfy req_REQ_BRK_009 by fu_F_5311_01;
    satisfy req_REQ_BRK_009 by fu_F_7255_01;
    satisfy req_REQ_BRK_010 by fu_F_7211_04;
    satisfy req_REQ_BRK_010 by fu_F_722A_01;
    satisfy req_REQ_BRK_010 by fu_F_722B_01;
    satisfy req_REQ_BRK_011 by fu_F_7211_04;
    satisfy req_REQ_BRK_011 by fu_F_7255_01;
    satisfy req_REQ_BRK_012 by fu_F_7142_01;
    satisfy req_REQ_BRK_012 by fu_F_7131_01;
    satisfy req_REQ_BRK_012 by fu_F_7100_01;
    satisfy req_REQ_BRK_013 by fu_F_722B_01;
    satisfy req_REQ_BRK_013 by fu_F_722C_01;
    satisfy req_REQ_BRK_013 by fu_F_7255_01;
    satisfy req_REQ_BRK_014 by fu_F_8152_01;
    satisfy req_REQ_BRK_014 by fu_F_8152_02;
    satisfy req_REQ_BRK_014 by fu_F_8128_01;
    satisfy req_REQ_BRK_014 by fu_F_722B_01;
    satisfy req_REQ_BRK_014 by fu_F_722C_01;
    satisfy req_REQ_BRK_015 by fu_F_7211_04;
    satisfy req_REQ_BRK_015 by fu_F_7226_01;
    satisfy req_REQ_BRK_015 by fu_F_7255_01;
    satisfy req_REQ_BRK_015 by fu_F_8152_01;
    satisfy req_REQ_ENE_002 by fu_F_X113_01;
    satisfy req_REQ_ENE_002 by fu_F_X112_03;
    satisfy req_REQ_ENE_002 by fu_F_8122_03;
    satisfy req_REQ_ENE_003 by fu_F_X121_02;
    satisfy req_REQ_ENE_003 by fu_F_X112_03;
    satisfy req_REQ_ENE_003 by fu_F_8122_03;
    satisfy req_REQ_ENE_003 by fu_F_8128_03;
    satisfy req_REQ_ENE_004 by fu_F_X122_01;
    satisfy req_REQ_ENE_004 by fu_F_X112_01;
    satisfy req_REQ_ENE_005 by fu_F_X121_01;
    satisfy req_REQ_ENE_005 by fu_F_X112_01;
    satisfy req_REQ_ENE_006 by fu_F_X124_01;
    satisfy req_REQ_ENE_007 by fu_F_X124_01;
    satisfy req_REQ_ENE_007 by fu_F_X112_02;
    satisfy req_REQ_ENE_008 by fu_F_X123_01;
    satisfy req_REQ_ENE_008 by fu_F_X112_02;
    satisfy req_REQ_ENE_009 by fu_F_X112_02;
    satisfy req_REQ_ENE_009 by fu_F_X113_01;
    satisfy req_PRJ_BRK_001 by fu_F_7211_01;
    satisfy req_PRJ_BRK_001 by fu_F_7211_02;
    satisfy req_PRJ_BRK_001 by fu_F_7211_03;
    satisfy req_PRJ_BRK_001 by fu_F_7255_01;
    satisfy req_PRJ_BRK_001 by fu_F_5311_01;
    satisfy req_PRJ_ENE_002 by fu_F_X112_02;
    satisfy req_PRJ_ENE_002 by fu_F_X112_01;
    satisfy req_PRJ_ENE_002 by fu_F_X121_01;
    satisfy req_PRJ_ENE_003 by fu_F_X123_01;
    satisfy req_PRJ_ENE_003 by fu_F_X112_02;
    satisfy req_PRJ_PWR_001 by fu_F_4111_01;
    satisfy req_PRJ_PWR_001 by fu_F_4511_01;
    satisfy req_PRJ_PWR_001 by fu_F_5131_01;
    satisfy req_PRJ_PWR_001 by fu_F_5132_01;
    satisfy req_REQ_TRAC_001 by fu_F_3100_01;
    satisfy req_REQ_TRAC_001 by fu_F_3112_01;
    satisfy req_REQ_TRAC_001 by fu_F_3120_01;
    satisfy req_REQ_TRAC_001 by fu_F_3121_01;
    satisfy req_REQ_TRAC_001 by fu_F_3500_01;
    satisfy req_REQ_TRAC_001 by fu_F_3510_01;
    satisfy req_REQ_TRAC_001 by fu_F_3511_01;
    satisfy req_REQ_TRAC_001 by fu_F_3512_01;
    satisfy req_REQ_TRAC_001 by fu_F_3514_01;
    satisfy req_REQ_TRAC_001 by fu_F_3600_01;
    satisfy req_REQ_TRAC_001 by fu_F_3640_01;
    satisfy req_REQ_TRAC_001 by fu_F_3641_01;
    satisfy req_REQ_TRAC_001 by fu_F_3643_01;
    satisfy req_REQ_TRAC_001 by fu_F_3644_01;
    satisfy req_REQ_TRAC_001 by fu_F_5300_01;
    satisfy req_REQ_TRAC_001 by fu_F_5310_01;
    satisfy req_REQ_TRAC_003 by fu_F_3641_01;
    satisfy req_REQ_TRAC_003 by fu_F_3643_01;
    satisfy req_REQ_TRAC_003 by fu_F_3644_01;
    satisfy req_REQ_TRAC_004 by fu_F_3100_01;
    satisfy req_REQ_TRAC_004 by fu_F_3112_01;
    satisfy req_REQ_TRAC_004 by fu_F_3120_01;
    satisfy req_REQ_TRAC_004 by fu_F_3121_01;
    satisfy req_REQ_TRAC_004 by fu_F_3500_01;
    satisfy req_REQ_TRAC_004 by fu_F_3510_01;
    satisfy req_REQ_TRAC_004 by fu_F_3511_01;
    satisfy req_REQ_TRAC_004 by fu_F_3512_01;
    satisfy req_REQ_TRAC_004 by fu_F_3514_01;
    satisfy req_REQ_TRAC_004 by fu_F_4500_01;
    satisfy req_REQ_TRAC_004 by fu_F_4510_01;
    satisfy req_REQ_TRAC_004 by fu_F_4513_01;
    satisfy req_REQ_TRAC_004 by fu_F_5300_01;
    satisfy req_REQ_TRAC_004 by fu_F_5310_01;
    satisfy req_REQ_BRK_001 by fu_F_3111_01;
    satisfy req_REQ_BRK_001 by fu_F_3130_01;
    satisfy req_REQ_BRK_001 by fu_F_3131_01;
    satisfy req_REQ_BRK_001 by fu_F_3132_01;
    satisfy req_REQ_BRK_001 by fu_F_3133_01;
    satisfy req_REQ_BRK_001 by fu_F_7252_01;
    satisfy req_REQ_BRK_001 by fu_F_7254_01;
    satisfy req_REQ_BRK_004 by fu_F_3130_01;
    satisfy req_REQ_BRK_004 by fu_F_3131_01;
    satisfy req_REQ_BRK_004 by fu_F_3132_01;
    satisfy req_REQ_BRK_004 by fu_F_3133_01;
    satisfy req_REQ_ENE_001 by fu_F_X110_01;
    satisfy req_REQ_ENE_001 by fu_F_X111_01;
    satisfy req_REQ_ENE_001 by fu_F_X111_02;
    satisfy req_REQ_ENE_005 by fu_F_8166_01;
    satisfy req_REQ_ENE_005 by fu_F_8166_02;
    satisfy req_REQ_ENE_005 by fu_F_8166_03;
    satisfy req_REQ_ENE_005 by fu_F_8166_04;
    satisfy req_PRJ_PWR_001 by fu_F_4100_01;
    satisfy req_PRJ_PWR_001 by fu_F_4110_01;
    satisfy req_PRJ_PWR_001 by fu_F_4200_01;
    satisfy req_PRJ_PWR_001 by fu_F_4210_01;
    satisfy req_PRJ_PWR_001 by fu_F_4211_01;
    satisfy req_PRJ_PWR_001 by fu_F_4212_01;
    satisfy req_DRV_TRAC_001 by fu_F_3100_01;
    satisfy req_DRV_TRAC_001 by fu_F_3110_01;
    satisfy req_DRV_TRAC_001 by fu_F_3112_01;
    satisfy req_DRV_TRAC_001 by fu_F_3120_01;
    satisfy req_DRV_TRAC_001 by fu_F_3121_01;
    satisfy req_DRV_TRAC_001 by fu_F_3500_01;
    satisfy req_DRV_TRAC_001 by fu_F_3510_01;
    satisfy req_DRV_TRAC_001 by fu_F_3511_01;
    satisfy req_DRV_TRAC_001 by fu_F_3512_01;
    satisfy req_DRV_TRAC_001 by fu_F_3514_01;
    satisfy req_DRV_TRAC_002 by fu_F_3800_01;
    satisfy req_DRV_TRAC_002 by fu_F_3810_01;
    satisfy req_DRV_TRAC_002 by fu_F_3811_01;
    satisfy req_DRV_TRAC_002 by fu_F_3811_02;
    satisfy req_DRV_TRAC_002 by fu_F_3813_01;
    satisfy req_DRV_TRAC_002 by fu_F_3814_01;
    satisfy req_DRV_TRAC_002 by fu_F_D13B_01;
    satisfy req_DRV_PWR_001 by fu_F_4100_01;
    satisfy req_DRV_PWR_001 by fu_F_4110_01;
    satisfy req_DRV_PWR_001 by fu_F_411C_01;
    satisfy req_DRV_PWR_001 by fu_F_411C_02;
    satisfy req_DRV_PWR_001 by fu_F_4200_01;
    satisfy req_DRV_PWR_001 by fu_F_4210_01;
    satisfy req_DRV_PWR_001 by fu_F_4211_01;
    satisfy req_DRV_PWR_001 by fu_F_4212_01;
    satisfy req_DRV_PWR_001 by fu_F_4230_01;
    satisfy req_DRV_PWR_001 by fu_F_4235_01;
    satisfy req_DRV_PWR_001 by fu_F_4236_01;
    satisfy req_DRV_PWR_001 by fu_F_4238_01;
    satisfy req_DRV_PWR_001 by fu_F_4238_02;
    satisfy req_DRV_PWR_001 by fu_F_4238_03;
    satisfy req_DRV_PWR_001 by fu_F_4239_01;
    satisfy req_DRV_PWR_001 by fu_F_4239_02;
    satisfy req_DRV_PWR_001 by fu_F_4239_03;
    satisfy req_DRV_PWR_001 by fu_F_4240_01;
    satisfy req_DRV_PWR_001 by fu_F_4241_01;
    satisfy req_DRV_PWR_001 by fu_F_4241_02;
    satisfy req_DRV_PWR_001 by fu_F_4241_03;
    satisfy req_DRV_PWR_002 by fu_F_4400_01;
    satisfy req_DRV_PWR_002 by fu_F_4410_01;
    satisfy req_DRV_PWR_002 by fu_F_4411_01;
    satisfy req_DRV_PWR_002 by fu_F_4412_01;
    satisfy req_DRV_PWR_002 by fu_F_4413_01;
    satisfy req_DRV_PWR_003 by fu_F_4500_01;
    satisfy req_DRV_PWR_003 by fu_F_4510_01;
    satisfy req_DRV_PWR_003 by fu_F_4513_01;
    satisfy req_DRV_PWR_003 by fu_F_4517_01;
    satisfy req_DRV_PWR_003 by fu_F_4518_01;
    satisfy req_DRV_PWR_003 by fu_F_4518_02;
    satisfy req_DRV_TRAC_003 by fu_F_5100_01;
    satisfy req_DRV_TRAC_003 by fu_F_5110_01;
    satisfy req_DRV_TRAC_003 by fu_F_5111_01;
    satisfy req_DRV_TRAC_003 by fu_F_5111_02;
    satisfy req_DRV_TRAC_003 by fu_F_5111_03;
    satisfy req_DRV_TRAC_003 by fu_F_5111_04;
    satisfy req_DRV_TRAC_003 by fu_F_5112_02;
    satisfy req_DRV_TRAC_003 by fu_F_5112_03;
    satisfy req_DRV_TRAC_003 by fu_F_5112_04;
    satisfy req_DRV_TRAC_003 by fu_F_5113_01;
    satisfy req_DRV_TRAC_003 by fu_F_5130_01;
    satisfy req_DRV_TRAC_003 by fu_F_5131_02;
    satisfy req_DRV_TRAC_003 by fu_F_5132_02;
    satisfy req_DRV_TRAC_004 by fu_F_5120_01;
    satisfy req_DRV_TRAC_004 by fu_F_5121_01;
    satisfy req_DRV_TRAC_004 by fu_F_5122_01;
    satisfy req_DRV_TRAC_004 by fu_F_5133_01;
    satisfy req_DRV_TRAC_004 by fu_F_5133_02;
    satisfy req_DRV_TRAC_004 by fu_F_5133_03;
    satisfy req_DRV_TRAC_004 by fu_F_5140_01;
    satisfy req_DRV_TRAC_004 by fu_F_5142_01;
    satisfy req_DRV_TRAC_004 by fu_F_5142_02;
    satisfy req_DRV_TRAC_004 by fu_F_5145_01;
    satisfy req_DRV_BRK_001 by fu_F_7100_01;
    satisfy req_DRV_BRK_001 by fu_F_7120_01;
    satisfy req_DRV_BRK_001 by fu_F_7124_01;
    satisfy req_DRV_BRK_001 by fu_F_7130_01;
    satisfy req_DRV_BRK_001 by fu_F_7131_01;
    satisfy req_DRV_BRK_001 by fu_F_7140_01;
    satisfy req_DRV_BRK_001 by fu_F_7142_01;
    satisfy req_DRV_BRK_002 by fu_F_7200_01;
    satisfy req_DRV_BRK_002 by fu_F_7210_01;
    satisfy req_DRV_BRK_002 by fu_F_7213_01;
    satisfy req_DRV_BRK_002 by fu_F_7220_01;
    satisfy req_DRV_BRK_002 by fu_F_7222_01;
    satisfy req_DRV_BRK_002 by fu_F_7223_01;
    satisfy req_DRV_BRK_002 by fu_F_7225_01;
    satisfy req_DRV_BRK_002 by fu_F_7227_01;
    satisfy req_DRV_BRK_002 by fu_F_7228_01;
    satisfy req_DRV_BRK_002 by fu_F_7229_01;
    satisfy req_DRV_BRK_002 by fu_F_7250_01;
    satisfy req_DRV_BRK_002 by fu_F_7252_01;
    satisfy req_DRV_BRK_002 by fu_F_7254_01;
    satisfy req_DRV_BRK_002 by fu_F_7280_01;
    satisfy req_DRV_BRK_002 by fu_F_7281_01;
    satisfy req_DRV_BRK_002 by fu_F_7284_01;
    satisfy req_DRV_BRK_002 by fu_F_7285_01;
    satisfy req_DRV_CTL_001 by fu_F_D100_01;
    satisfy req_DRV_CTL_001 by fu_F_D110_01;
    satisfy req_DRV_CTL_001 by fu_F_D112_01;
    satisfy req_DRV_CTL_001 by fu_F_D113_01;
    satisfy req_DRV_CTL_001 by fu_F_D114_01;
    satisfy req_DRV_CTL_001 by fu_F_D120_01;
    satisfy req_DRV_CTL_001 by fu_F_D130_01;
    satisfy req_DRV_CTL_001 by fu_F_E100_01;
    satisfy req_DRV_CTL_001 by fu_F_8127_01;
    satisfy req_DRV_CTL_001 by fu_F_8127_02;
    satisfy req_DRV_CTL_002 by fu_F_8100_01;
    satisfy req_DRV_CTL_002 by fu_F_8120_01;
    satisfy req_DRV_CTL_002 by fu_F_8121_01;
    satisfy req_DRV_CTL_002 by fu_F_8121_02;
    satisfy req_DRV_CTL_002 by fu_F_8121_03;
    satisfy req_DRV_CTL_002 by fu_F_8122_01;
    satisfy req_DRV_CTL_002 by fu_F_8122_02;
    satisfy req_DRV_CTL_002 by fu_F_8122_04;
    satisfy req_DRV_CTL_002 by fu_F_8122_05;
    satisfy req_DRV_CTL_002 by fu_F_8125_01;
    satisfy req_DRV_CTL_002 by fu_F_8125_02;
    satisfy req_DRV_CTL_002 by fu_F_8125_03;
    satisfy req_DRV_CTL_002 by fu_F_8125_04;
    satisfy req_DRV_CTL_002 by fu_F_8128_01;
    satisfy req_DRV_CTL_002 by fu_F_8128_02;
    satisfy req_DRV_CTL_002 by fu_F_8128_03;
    satisfy req_DRV_CTL_002 by fu_F_8160_01;
    satisfy req_DRV_CTL_003 by fu_F_8150_01;
    satisfy req_DRV_CTL_003 by fu_F_8151_01;
    satisfy req_DRV_CTL_003 by fu_F_8151_02;
    satisfy req_DRV_CTL_003 by fu_F_8152_01;
    satisfy req_DRV_CTL_003 by fu_F_8152_02;
    satisfy req_DRV_CTL_003 by fu_F_8154_01;
    satisfy req_DRV_CTL_003 by fu_F_8154_02;

    // Coverage-audit implementation-support links are kept distinct from the 289 formal satisfaction mappings.
    item def FunctionImplementationSupportTrace {
        attribute functionId : String;
        attribute functionName : String;
        attribute requirementIds : String;
        attribute coverageType : String;
        attribute evidence : String;
    }

    item implementationSupport_001 : FunctionImplementationSupportTrace {
        attribute :>> functionId = "FN_F_3000_01";
        attribute :>> functionName = "转换能量/物理量、控制运行";
        attribute :>> requirementIds = "REQ-TRAC-001；REQ-TRAC-004";
        attribute :>> coverageType = "IMPLEMENTATION_SUPPORT";
        attribute :>> evidence = "Function覆盖审计中的实现支持来源；不是289条正式Requirement→Function映射之一。";
    }

    item implementationSupport_002 : FunctionImplementationSupportTrace {
        attribute :>> functionId = "FN_F_4000_01";
        attribute :>> functionName = "转换能量/物理量、控制运行";
        attribute :>> requirementIds = "PRJ-PWR-001";
        attribute :>> coverageType = "IMPLEMENTATION_SUPPORT";
        attribute :>> evidence = "Function覆盖审计中的实现支持来源；不是289条正式Requirement→Function映射之一。";
    }

    item implementationSupport_003 : FunctionImplementationSupportTrace {
        attribute :>> functionId = "FN_F_5000_01";
        attribute :>> functionName = "转换能量/物理量、控制运行";
        attribute :>> requirementIds = "REQ-TRAC-004";
        attribute :>> coverageType = "IMPLEMENTATION_SUPPORT";
        attribute :>> evidence = "Function覆盖审计中的实现支持来源；不是289条正式Requirement→Function映射之一。";
    }

    item implementationSupport_004 : FunctionImplementationSupportTrace {
        attribute :>> functionId = "FN_F_7000_01";
        attribute :>> functionName = "转换能量/物理量、控制运行";
        attribute :>> requirementIds = "REQ-BRK-001";
        attribute :>> coverageType = "IMPLEMENTATION_SUPPORT";
        attribute :>> evidence = "Function覆盖审计中的实现支持来源；不是289条正式Requirement→Function映射之一。";
    }

    item implementationSupport_005 : FunctionImplementationSupportTrace {
        attribute :>> functionId = "FN_F_8000_01";
        attribute :>> functionName = "控制运行、实施保护与限制";
        attribute :>> requirementIds = "DRV-CTL-002；DRV-CTL-003";
        attribute :>> coverageType = "IMPLEMENTATION_SUPPORT";
        attribute :>> evidence = "Function覆盖审计中的实现支持来源；不是289条正式Requirement→Function映射之一。";
    }

    item implementationSupport_006 : FunctionImplementationSupportTrace {
        attribute :>> functionId = "FN_F_D000_01";
        attribute :>> functionName = "控制运行";
        attribute :>> requirementIds = "DRV-CTL-001";
        attribute :>> coverageType = "IMPLEMENTATION_SUPPORT";
        attribute :>> evidence = "Function覆盖审计中的实现支持来源；不是289条正式Requirement→Function映射之一。";
    }

    item implementationSupport_007 : FunctionImplementationSupportTrace {
        attribute :>> functionId = "FN_F_E000_01";
        attribute :>> functionName = "控制运行";
        attribute :>> requirementIds = "DRV-CTL-001";
        attribute :>> coverageType = "IMPLEMENTATION_SUPPORT";
        attribute :>> evidence = "Function覆盖审计中的实现支持来源；不是289条正式Requirement→Function映射之一。";
    }

    item implementationSupport_008 : FunctionImplementationSupportTrace {
        attribute :>> functionId = "FN_F_X000_01";
        attribute :>> functionName = "实现车载再生能量回收与利用";
        attribute :>> requirementIds = "REQ-ENE-001；PRJ-ENE-001";
        attribute :>> coverageType = "IMPLEMENTATION_SUPPORT";
        attribute :>> evidence = "Function覆盖审计中的实现支持来源；不是289条正式Requirement→Function映射之一。";
    }

    item implementationSupport_009 : FunctionImplementationSupportTrace {
        attribute :>> functionId = "FN_F_X120_01";
        attribute :>> functionName = "储存与释放能量、检测运行参数";
        attribute :>> requirementIds = "REQ-ENE-001；REQ-ENE-003";
        attribute :>> coverageType = "IMPLEMENTATION_SUPPORT";
        attribute :>> evidence = "Function覆盖审计中的实现支持来源；不是289条正式Requirement→Function映射之一。";
    }

    item implementationSupport_010 : FunctionImplementationSupportTrace {
        attribute :>> functionId = "FN_F_X130_01";
        attribute :>> functionName = "传递能量/介质";
        attribute :>> requirementIds = "REQ-ENE-001；REQ-ENE-003";
        attribute :>> coverageType = "IMPLEMENTATION_SUPPORT";
        attribute :>> evidence = "Function覆盖审计中的实现支持来源；不是289条正式Requirement→Function映射之一。";
    }

    item implementationSupport_011 : FunctionImplementationSupportTrace {
        attribute :>> functionId = "FN_F_X131_01";
        attribute :>> functionName = "传递储能主接触器电能";
        attribute :>> requirementIds = "REQ-ENE-001；REQ-ENE-003";
        attribute :>> coverageType = "IMPLEMENTATION_SUPPORT";
        attribute :>> evidence = "Function覆盖审计中的实现支持来源；不是289条正式Requirement→Function映射之一。";
    }

    item implementationSupport_012 : FunctionImplementationSupportTrace {
        attribute :>> functionId = "FN_F_X132_01";
        attribute :>> functionName = "传递储能预充电组件电能";
        attribute :>> requirementIds = "REQ-ENE-001；REQ-ENE-003";
        attribute :>> coverageType = "IMPLEMENTATION_SUPPORT";
        attribute :>> evidence = "Function覆盖审计中的实现支持来源；不是289条正式Requirement→Function映射之一。";
    }

    item implementationSupport_013 : FunctionImplementationSupportTrace {
        attribute :>> functionId = "FN_F_X133_01";
        attribute :>> functionName = "传递储能支路保护组件电能";
        attribute :>> requirementIds = "REQ-ENE-001；REQ-ENE-003";
        attribute :>> coverageType = "IMPLEMENTATION_SUPPORT";
        attribute :>> evidence = "Function覆盖审计中的实现支持来源；不是289条正式Requirement→Function映射之一。";
    }

}
